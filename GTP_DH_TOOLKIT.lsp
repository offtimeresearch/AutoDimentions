; GTP_DH_TOOLKIT.LSP
; Permanent AutoLISP toolkit for AutoCAD / AutoCAD Mechanical
; ONE FILE ONLY - update this file in place.
;
; Commands:
;   GTPPIPE   - Create Isoplus pre-insulated 3D pipe from a prepared route
;   GTPMITER  - Extend/trim two selected route ends to their axis intersection
;   GTPMITTER - Alias for GTPMITER
;   GTPUNITS  - Set/check catalogue-mm to drawing-unit conversion
;   GTPLAYER  - Create/check GTP layers
;   GTPHELP   - Show loaded commands
;
; Route rule:
;   GTPPIPE ignores duplicate and nearly-collinear intermediate route vertices.
;   Only real direction changes are treated as bend corners.
;   The original selected polyline is NOT modified.
;   Route cleanup is fail-safe: if cleanup fails, the original route is used.
;   True straight runs are still split by catalogue stock length for real spool joints.

(vl-load-com)

; -----------------------------------------------------------------------------
; CATALOGUE DATA - millimetres
; -----------------------------------------------------------------------------
(setq *gtp-pipe-db*
  '(
    (20  26.9  90  110 125)
    (25  33.7  90  110 125)
    (32  42.4  110 125 140)
    (40  48.3  110 125 140)
    (50  60.3  125 140 160)
    (65  76.1  140 160 180)
    (80  88.9  160 180 200)
    (100 114.3 200 225 250)
    (125 139.7 225 250 280)
    (150 168.3 250 280 315)
    (200 219.1 315 355 400)
    (250 273.0 400 450 500)
    (300 323.9 450 500 560)
    (350 355.6 500 560 630)
    (400 406.4 560 630 710)
    (450 457.2 630 710 800)
    (500 508.0 710 800 900)
    (600 610.0 800 900 1000)
  )
)

(setq *gtp-elbow-db*
  '(
    (20  600.0 1000.0) (25  600.0 1000.0) (32  600.0 1000.0)
    (40  600.0 1000.0) (50  600.0 1000.0) (65  600.0 1000.0)
    (80  600.0 1000.0) (100 700.0 1000.0) (125 750.0 1000.0)
    (150 800.0 1000.0) (200 nil   1000.0) (250 nil   1000.0)
    (300 nil   1000.0) (350 nil   1000.0) (400 nil   1000.0)
    (450 nil   1100.0) (500 nil   1200.0) (600 nil   1300.0)
  )
)

(setq *gtp-max-pipe-length-mm* 12000.0)
(setq *gtp-end-cutback-mm* 220.0)
(setq *gtp-standard-bend-radius-factor* 3.0)
(setq *gtp-min-elbow-straight-mm* 50.0)
(setq *gtp-straight-angle-tol-deg* 2.0)
(setq *gtp-duplicate-point-tol* 1e-8)
(setq *gtp-mm-to-du* 1.0)
(setq *gtp-drawing-unit-name* "millimetres")
(setq *gtp-pipe-color* 1)
(setq *gtp-flow-type* "Flow")

(defun gtp:unit-info-from-insunits (u)
  (cond
    ((= u 1)  (list "inches" (/ 1.0 25.4)))
    ((= u 2)  (list "feet" (/ 1.0 304.8)))
    ((= u 4)  (list "millimetres" 1.0))
    ((= u 5)  (list "centimetres" 0.1))
    ((= u 6)  (list "metres" 0.001))
    ((= u 7)  (list "kilometres" 0.000001))
    ((= u 10) (list "yards" (/ 1.0 914.4)))
    ((= u 14) (list "decimetres" 0.01))
    ((= u 15) (list "decametres" 0.0001))
    ((= u 16) (list "hectometres" 0.00001))
    (T nil)
  )
)
(defun gtp:manual-unit-info (/ s)
  (initget "MM CM M Inch Feet")
  (setq s (getkword "\nDrawing unit [MM/CM/M/Inch/Feet] <MM>: "))
  (if (null s) (setq s "MM"))
  (cond
    ((= s "MM")   (list "millimetres" 1.0))
    ((= s "CM")   (list "centimetres" 0.1))
    ((= s "M")    (list "metres" 0.001))
    ((= s "Inch") (list "inches" (/ 1.0 25.4)))
    ((= s "Feet") (list "feet" (/ 1.0 304.8)))
  )
)
(defun gtp:setup-units (/ s info)
  (initget "Auto MM CM M Inch Feet")
  (setq s (getkword "\nCatalogue is mm. Drawing unit [Auto/MM/CM/M/Inch/Feet] <Auto>: "))
  (if (null s) (setq s "Auto"))
  (cond
    ((= s "Auto")
      (setq info (gtp:unit-info-from-insunits (getvar "INSUNITS")))
      (if (null info) (setq info (gtp:manual-unit-info)))
    )
    ((= s "MM")   (setq info (list "millimetres" 1.0)))
    ((= s "CM")   (setq info (list "centimetres" 0.1)))
    ((= s "M")    (setq info (list "metres" 0.001)))
    ((= s "Inch") (setq info (list "inches" (/ 1.0 25.4))))
    ((= s "Feet") (setq info (list "feet" (/ 1.0 304.8))))
  )
  (setq *gtp-drawing-unit-name* (car info))
  (setq *gtp-mm-to-du* (cadr info))
  (princ (strcat "\nGTP scale: 1000 mm = " (rtos (* 1000.0 *gtp-mm-to-du*) 2 6) " drawing units [" *gtp-drawing-unit-name* "]."))
  info
)
(defun gtp:mm (x) (* x *gtp-mm-to-du*))
(defun c:GTPUNITS () (gtp:setup-units) (princ))

(defun gtp:ensure-layer (name color / doc lays lay)
  (setq doc (vla-get-ActiveDocument (vlax-get-acad-object)))
  (setq lays (vla-get-Layers doc))
  (if (tblsearch "LAYER" name) (setq lay (vla-Item lays name)) (setq lay (vla-Add lays name)))
  (if color (vla-put-Color lay color))
  (vl-catch-all-apply 'vla-put-LayerOn (list lay :vlax-true))
  (vl-catch-all-apply 'vla-put-Freeze (list lay :vlax-false))
  (vl-catch-all-apply 'vla-put-Lock (list lay :vlax-false))
  lay
)
(defun gtp:layers ()
  (gtp:ensure-layer "GTP-PIPE-CASING" 8)
  (gtp:ensure-layer "GTP-PIPE-INSULATION" 2)
  (gtp:ensure-layer "GTP-PIPE-CARRIER" 1)
  (gtp:ensure-layer "GTP-PIPE-CENTRELINE" 4)
  (princ)
)
(defun c:GTPLAYER () (gtp:layers) (princ "\nGTP layers ready and visible.") (princ))

(defun gtp:vadd (a b) (mapcar '+ a b))
(defun gtp:vsub (a b) (mapcar '- a b))
(defun gtp:vscale (v s) (mapcar '(lambda (x) (* x s)) v))
(defun gtp:dot (a b) (+ (* (car a) (car b)) (* (cadr a) (cadr b)) (* (caddr a) (caddr b))))
(defun gtp:vmag (v) (sqrt (gtp:dot v v)))
(defun gtp:vunit (v / m) (setq m (gtp:vmag v)) (if (> m 1e-12) (gtp:vscale v (/ 1.0 m)) '(0.0 0.0 1.0)))
(defun gtp:cross (a b)
  (list
    (- (* (cadr a) (caddr b)) (* (caddr a) (cadr b)))
    (- (* (caddr a) (car b)) (* (car a) (caddr b)))
    (- (* (car a) (cadr b)) (* (cadr a) (car b)))
  )
)
(defun gtp:rad->deg (a) (* a (/ 180.0 pi)))
(defun gtp:tan (a / c) (setq c (cos a)) (if (< (abs c) 1e-12) 1e99 (/ (sin a) c)))
(defun gtp:variant (lst)
  (vlax-make-variant
    (vlax-safearray-fill (vlax-make-safearray vlax-vbDouble '(0 . 2)) lst)
  )
)
(defun gtp:axis-matrix (p1 p2 / z ref x y mid)
  (setq z (gtp:vunit (gtp:vsub p2 p1)))
  (setq mid (mapcar '(lambda (a b) (/ (+ a b) 2.0)) p1 p2))
  (if (> (abs (caddr z)) 0.999) (setq ref '(0.0 1.0 0.0)) (setq ref '(0.0 0.0 1.0)))
  (setq x (gtp:vunit (gtp:cross ref z)))
  (setq y (gtp:cross z x))
  (list
    (list (car x) (car y) (car z) (car mid))
    (list (cadr x) (cadr y) (cadr z) (cadr mid))
    (list (caddr x) (caddr y) (caddr z) (caddr mid))
    (list 0.0 0.0 0.0 1.0)
  )
)
(defun gtp:frame-z (origin z / ref x y)
  (setq z (gtp:vunit z))
  (if (> (abs (caddr z)) 0.999) (setq ref '(0.0 1.0 0.0)) (setq ref '(0.0 0.0 1.0)))
  (setq x (gtp:vunit (gtp:cross ref z)))
  (setq y (gtp:cross z x))
  (list
    (list (car x) (car y) (car z) (car origin))
    (list (cadr x) (cadr y) (cadr z) (cadr origin))
    (list (caddr x) (caddr y) (caddr z) (caddr origin))
    (list 0.0 0.0 0.0 1.0)
  )
)
(defun gtp:frame-xyz (origin x y z)
  (list
    (list (car x) (car y) (car z) (car origin))
    (list (cadr x) (cadr y) (cadr z) (cadr origin))
    (list (caddr x) (caddr y) (caddr z) (caddr origin))
    (list 0.0 0.0 0.0 1.0)
  )
)

(defun gtp:make-cylinder (p1 p2 dia layer / doc ms len obj)
  (setq len (distance p1 p2))
  (if (> len 1e-8)
    (progn
      (setq doc (vla-get-ActiveDocument (vlax-get-acad-object)))
      (setq ms (vla-get-ModelSpace doc))
      (setq obj (vla-AddCylinder ms (gtp:variant '(0.0 0.0 0.0)) (/ dia 2.0) len))
      (vla-TransformBy obj (vlax-tmatrix (gtp:axis-matrix p1 p2)))
      (vla-put-Layer obj layer)
      (vla-put-Color obj *gtp-pipe-color*)
      obj
    )
  )
)
(defun gtp:safe-delete (obj) (if obj (vl-catch-all-apply 'vla-Delete (list obj))))
(defun gtp:make-circle-region (center normal radius / doc ms cir arr regs reg)
  (setq doc (vla-get-ActiveDocument (vlax-get-acad-object)))
  (setq ms (vla-get-ModelSpace doc))
  (setq cir (vla-AddCircle ms (gtp:variant '(0.0 0.0 0.0)) radius))
  (vla-TransformBy cir (vlax-tmatrix (gtp:frame-z center normal)))
  (setq arr (vlax-make-safearray vlax-vbObject '(0 . 0)))
  (vlax-safearray-put-element arr 0 cir)
  (setq regs (vl-catch-all-apply 'vla-AddRegion (list ms arr)))
  (if (vl-catch-all-error-p regs)
    (progn (gtp:safe-delete cir) nil)
    (progn (setq reg (vlax-safearray-get-element (vlax-variant-value regs) 0)) (gtp:safe-delete cir) reg)
  )
)
(defun gtp:make-arc-path (center t1 normal radius phi / doc ms x y arc)
  (setq doc (vla-get-ActiveDocument (vlax-get-acad-object)))
  (setq ms (vla-get-ModelSpace doc))
  (setq x (gtp:vunit (gtp:vsub t1 center)))
  (setq y (gtp:cross normal x))
  (setq arc (vla-AddArc ms (gtp:variant '(0.0 0.0 0.0)) radius 0.0 phi))
  (vla-TransformBy arc (vlax-tmatrix (gtp:frame-xyz center x y normal)))
  arc
)
(defun gtp:sweep-arc (center t1 normal tangent radius phi dia layer / doc ms path reg sol)
  (setq doc (vla-get-ActiveDocument (vlax-get-acad-object)))
  (setq ms (vla-get-ModelSpace doc))
  (setq path (gtp:make-arc-path center t1 normal radius phi))
  (setq reg (gtp:make-circle-region t1 tangent (/ dia 2.0)))
  (if (and path reg) (setq sol (vl-catch-all-apply 'vla-AddExtrudedSolidAlongPath (list ms reg path))))
  (gtp:safe-delete reg)
  (gtp:safe-delete path)
  (if (or (null sol) (vl-catch-all-error-p sol)) nil (progn (vla-put-Layer sol layer) (vla-put-Color sol *gtp-pipe-color*) sol))
)
(defun gtp:arc-point (center x y radius a)
  (gtp:vadd center (gtp:vadd (gtp:vscale x (* radius (cos a))) (gtp:vscale y (* radius (sin a)))))
)
(defun gtp:segmented-arc (center t1 normal radius phi dia layer / x y seg i a0 a1 p0 p1 obj out)
  (setq x (gtp:vunit (gtp:vsub t1 center)))
  (setq y (gtp:cross normal x))
  (setq seg (max 8 (fix (+ 0.5 (* 18.0 (/ phi (/ pi 2.0)))))))
  (setq i 0 out '())
  (while (< i seg)
    (setq a0 (* phi (/ (float i) seg)) a1 (* phi (/ (float (1+ i)) seg)))
    (setq p0 (gtp:arc-point center x y radius a0) p1 (gtp:arc-point center x y radius a1))
    (setq obj (gtp:make-cylinder p0 p1 dia layer))
    (if obj (setq out (cons obj out)))
    (setq i (1+ i))
  )
  (reverse out)
)
(defun gtp:model-arc (center t1 normal tangent radius phi dia layer / obj fallback)
  (setq obj (vl-catch-all-apply 'gtp:sweep-arc (list center t1 normal tangent radius phi dia layer)))
  (if (and obj (not (vl-catch-all-error-p obj)))
    (list obj)
    (progn
      (setq fallback (vl-catch-all-apply 'gtp:segmented-arc (list center t1 normal radius phi dia layer)))
      (if (vl-catch-all-error-p fallback) nil fallback)
    )
  )
)

(defun gtp:find-dn (dn) (assoc dn *gtp-pipe-db*))
(defun gtp:casing-od (row series)
  (cond ((= series 1) (nth 2 row)) ((= series 2) (nth 3 row)) ((= series 3) (nth 4 row)))
)
(defun gtp:get-dn (/ dn row)
  (while (null row)
    (setq dn (getint "\nNominal DN [20/25/32/40/50/65/80/100/125/150/200/250/300/350/400/450/500/600]: "))
    (if dn (setq row (gtp:find-dn dn)))
    (if (and dn (null row)) (princ "\nDN not in current database."))
  )
  row
)
(defun gtp:get-series (/ s) (initget "1 2 3") (setq s (getkword "\nInsulation series [1/2/3] <2>: ")) (if s (atoi s) 2))
(defun gtp:get-mode (/ s) (initget "CASING FULL") (setq s (getkword "\nModel mode [CASING/FULL] <CASING>: ")) (if s s "CASING"))
(defun gtp:get-flow-type (/ s)
  (initget "Flow Return")
  (setq s (getkword "\nPipe duty [Flow/Return] <Flow>: "))
  (if (null s) (setq s "Flow"))
  (setq *gtp-flow-type* s *gtp-pipe-color* (if (= s "Flow") 1 5))
  (princ (strcat "\n" s " pipe colour: " (if (= s "Flow") "red." "blue.")))
  s
)
(defun gtp:get-elbow-style (/ s) (initget "Standard Short") (setq s (getkword "\nElbow leg [Standard/Short] <Standard>: ")) (if s s "Standard"))
(defun gtp:elbow-leg-mm (dn style / row short standard)
  (setq row (assoc dn *gtp-elbow-db*) short (nth 1 row) standard (nth 2 row))
  (if (= style "Short") (if short short standard) standard)
)
(defun gtp:make-elbow-spec (prev vertex next dn carrier casing style / d1 d2 cr cm dp phi deg leg0 maxleg leg normal desiredR minR minStraight tang maxR radius tanDist fs fe t1 t2 inward center)
  (setq d1 (gtp:vunit (gtp:vsub vertex prev)) d2 (gtp:vunit (gtp:vsub next vertex)))
  (setq cr (gtp:cross d1 d2) cm (gtp:vmag cr) dp (gtp:dot d1 d2) phi (atan cm dp) deg (gtp:rad->deg phi))
  (if (or (< deg 1.0) (> deg 175.0) (< cm 1e-10)) nil
    (progn
      (setq normal (gtp:vunit cr) leg0 (gtp:mm (gtp:elbow-leg-mm dn style)))
      (setq maxleg (min (* 0.45 (distance prev vertex)) (* 0.45 (distance vertex next))))
      (setq leg (min leg0 maxleg))
      (setq desiredR (* *gtp-standard-bend-radius-factor* carrier) minR (* 0.55 casing))
      (setq minStraight (min (* 0.25 leg) (max (gtp:mm *gtp-min-elbow-straight-mm*) (gtp:mm *gtp-end-cutback-mm*))))
      (setq tang (gtp:tan (/ phi 2.0)))
      (setq maxR (if (> tang 1e-10) (/ (max 0.0 (- leg minStraight)) tang) desiredR))
      (setq radius (min desiredR maxR))
      (if (< radius minR) nil
        (progn
          (setq tanDist (* radius tang))
          (setq fs (gtp:vadd vertex (gtp:vscale d1 (- leg))))
          (setq fe (gtp:vadd vertex (gtp:vscale d2 leg)))
          (setq t1 (gtp:vadd vertex (gtp:vscale d1 (- tanDist))))
          (setq t2 (gtp:vadd vertex (gtp:vscale d2 tanDist)))
          (setq inward (gtp:vunit (gtp:cross normal d1)) center (gtp:vadd t1 (gtp:vscale inward radius)))
          (list (cons 'radius radius) (cons 'phi phi) (cons 'deg deg) (cons 'd1 d1) (cons 'd2 d2) (cons 'normal normal) (cons 'start fs) (cons 'tan1 t1) (cons 'center center) (cons 'tan2 t2) (cons 'end fe) (cons 'clipped (< leg (- leg0 1e-8))))
        )
      )
    )
  )
)
(defun gtp:spec (key spec) (cdr (assoc key spec)))
(defun gtp:model-elbow (spec carrier casing mode / r phi d1 d2 normal fs t1 center t2 fe cut cut1 cut2 cs ce)
  (setq r (gtp:spec 'radius spec) phi (gtp:spec 'phi spec) d1 (gtp:spec 'd1 spec) d2 (gtp:spec 'd2 spec) normal (gtp:spec 'normal spec) fs (gtp:spec 'start spec) t1 (gtp:spec 'tan1 spec) center (gtp:spec 'center spec) t2 (gtp:spec 'tan2 spec) fe (gtp:spec 'end spec))
  (gtp:make-cylinder fs t1 carrier "GTP-PIPE-CARRIER")
  (gtp:model-arc center t1 normal d1 r phi carrier "GTP-PIPE-CARRIER")
  (gtp:make-cylinder t2 fe carrier "GTP-PIPE-CARRIER")
  (setq cut (gtp:mm *gtp-end-cutback-mm*) cut1 (min cut (* 0.80 (distance fs t1))) cut2 (min cut (* 0.80 (distance t2 fe))))
  (setq cs (gtp:vadd fs (gtp:vscale d1 cut1)) ce (gtp:vadd fe (gtp:vscale d2 (- cut2))))
  (gtp:make-cylinder cs t1 casing "GTP-PIPE-CASING")
  (gtp:model-arc center t1 normal d1 r phi casing "GTP-PIPE-CASING")
  (gtp:make-cylinder t2 ce casing "GTP-PIPE-CASING")
  (if (= mode "FULL")
    (progn
      (gtp:make-cylinder cs t1 casing "GTP-PIPE-INSULATION")
      (gtp:model-arc center t1 normal d1 r phi casing "GTP-PIPE-INSULATION")
      (gtp:make-cylinder t2 ce casing "GTP-PIPE-INSULATION")
    )
  )
)
(defun gtp:point-along (p1 p2 dist) (gtp:vadd p1 (gtp:vscale (gtp:vunit (gtp:vsub p2 p1)) dist)))
(defun gtp:model-spool (p1 p2 carrier casing mode / len cut c1 c2)
  (setq len (distance p1 p2) cut (gtp:mm *gtp-end-cutback-mm*))
  (if (>= (* 2.0 cut) len) (setq cut (/ len 4.0)))
  (setq c1 (gtp:point-along p1 p2 cut) c2 (gtp:point-along p1 p2 (- len cut)))
  (gtp:make-cylinder p1 p2 carrier "GTP-PIPE-CARRIER")
  (if (> (distance c1 c2) 1e-8)
    (progn
      (gtp:make-cylinder c1 c2 casing "GTP-PIPE-CASING")
      (if (= mode "FULL") (gtp:make-cylinder c1 c2 casing "GTP-PIPE-INSULATION"))
    )
  )
)
(defun gtp:model-segment (p1 p2 carrier casing mode / len dir pos piece s1 s2 count)
  (setq len (distance p1 p2) dir (gtp:vunit (gtp:vsub p2 p1)) pos 0.0 count 0)
  (while (< pos (- len 1e-8))
    (setq piece (min (gtp:mm *gtp-max-pipe-length-mm*) (- len pos)))
    (setq s1 (gtp:vadd p1 (gtp:vscale dir pos)) s2 (gtp:vadd p1 (gtp:vscale dir (+ pos piece))))
    (gtp:model-spool s1 s2 carrier casing mode)
    (setq pos (+ pos piece) count (1+ count))
  )
  count
)
(defun gtp:curve-points (ename / endParam i p pts)
  (setq endParam (vl-catch-all-apply 'vlax-curve-getEndParam (list ename)))
  (if (vl-catch-all-error-p endParam) nil
    (progn
      (setq i 0 pts '())
      (while (<= i (fix endParam))
        (setq p (vlax-curve-getPointAtParam ename i))
        (if p (setq pts (append pts (list p))))
        (setq i (1+ i))
      )
      pts
    )
  )
)
(defun gtp:remove-duplicate-route-points (pts / out lastp p)
  (setq out '() lastp nil)
  (foreach p pts
    (if (or (null lastp) (> (distance lastp p) *gtp-duplicate-point-tol*)) (progn (setq out (append out (list p))) (setq lastp p)))
  )
  out
)
(defun gtp:route-turn-angle-deg (a b c / u v cr dp)
  (setq u (gtp:vunit (gtp:vsub b a)) v (gtp:vunit (gtp:vsub c b)) cr (gtp:vmag (gtp:cross u v)) dp (gtp:dot u v))
  (gtp:rad->deg (atan cr dp))
)
(defun gtp:simplify-route-points (pts / originalCount cleaned duplicateRemoved n out i prev cur nxt ang straightRemoved)
  (setq originalCount (length pts) cleaned (gtp:remove-duplicate-route-points pts) duplicateRemoved (- originalCount (length cleaned)) straightRemoved 0)
  (if (<= (length cleaned) 2) (list cleaned duplicateRemoved 0)
    (progn
      (setq n (length cleaned) out (list (car cleaned)) i 1)
      (while (< i (1- n))
        (setq prev (nth (1- i) cleaned) cur (nth i cleaned) nxt (nth (1+ i) cleaned) ang (gtp:route-turn-angle-deg prev cur nxt))
        (if (<= ang *gtp-straight-angle-tol-deg*) (setq straightRemoved (1+ straightRemoved)) (setq out (append out (list cur))))
        (setq i (1+ i))
      )
      (setq out (append out (list (last cleaned))))
      (list out duplicateRemoved straightRemoved)
    )
  )
)
(defun gtp:safe-simplify-route-points (pts / r)
  (setq r (vl-catch-all-apply 'gtp:simplify-route-points (list pts)))
  (if (or (vl-catch-all-error-p r) (null r) (null (car r)) (< (length (car r)) 2))
    (progn (princ "\nRoute cleanup warning: cleanup failed, so the original route vertices will be used.") (list pts 0 0))
    r
  )
)
(defun gtp:model-corner-route (pts dn carrier casing mode style / n elbows i spec p1 p2 s e spoolCount elbowCount clippedCount)
  (setq n (length pts) elbows '() i 0 spoolCount 0 elbowCount 0 clippedCount 0)
  (while (< i n)
    (setq spec nil)
    (if (and (> i 0) (< i (1- n))) (setq spec (gtp:make-elbow-spec (nth (1- i) pts) (nth i pts) (nth (1+ i) pts) dn carrier casing style)))
    (if (and spec (gtp:spec 'clipped spec)) (setq clippedCount (1+ clippedCount)))
    (setq elbows (append elbows (list spec)) i (1+ i))
  )
  (setq i 0)
  (while (< i (1- n))
    (setq p1 (nth i pts) p2 (nth (1+ i) pts))
    (setq s (if (nth i elbows) (gtp:spec 'end (nth i elbows)) p1))
    (setq e (if (nth (1+ i) elbows) (gtp:spec 'start (nth (1+ i) elbows)) p2))
    (if (> (distance s e) 1e-8) (setq spoolCount (+ spoolCount (gtp:model-segment s e carrier casing mode))))
    (setq i (1+ i))
  )
  (setq i 1)
  (while (< i (1- n))
    (if (nth i elbows) (progn (gtp:model-elbow (nth i elbows) carrier casing mode) (setq elbowCount (1+ elbowCount))))
    (setq i (1+ i))
  )
  (list spoolCount elbowCount clippedCount)
)
(defun c:GTPPIPE (/ *error* old ent typ row dn series carrierMM casingMM carrier casing mode flowType style rawPts cleanInfo pts dupRemoved straightRemoved result)
  (vl-load-com)
  (defun *error* (msg)
    (if old (setvar "CMDECHO" old))
    (if (and msg (/= msg "Function cancelled") (/= msg "quit / exit abort")) (princ (strcat "\nGTPPIPE error: " msg)))
    (princ)
  )
  (setq old (getvar "CMDECHO")) (setvar "CMDECHO" 0) (gtp:layers)
  (setq ent (car (entsel "\nSelect prepared route LINE / 2D or 3D POLYLINE: ")))
  (if ent
    (progn
      (setq typ (cdr (assoc 0 (entget ent))))
      (if (member typ '("LINE" "LWPOLYLINE" "POLYLINE"))
        (progn
          (gtp:setup-units) (setq row (gtp:get-dn) dn (nth 0 row) carrierMM (nth 1 row) series (gtp:get-series) casingMM (gtp:casing-od row series))
          (setq carrier (gtp:mm carrierMM) casing (gtp:mm casingMM) mode (gtp:get-mode) flowType (gtp:get-flow-type) style (gtp:get-elbow-style))
          (setq rawPts (gtp:curve-points ent))
          (if (and rawPts (>= (length rawPts) 2))
            (progn
              (setq cleanInfo (gtp:safe-simplify-route-points rawPts) pts (nth 0 cleanInfo) dupRemoved (nth 1 cleanInfo) straightRemoved (nth 2 cleanInfo))
              (princ (strcat "\nRoute cleanup: " (itoa (length rawPts)) " input vertex/vertices -> " (itoa (length pts)) " modelling vertex/vertices."))
              (if (> (+ dupRemoved straightRemoved) 0) (princ (strcat " Ignored " (itoa dupRemoved) " duplicate and " (itoa straightRemoved) " nearly-collinear intermediate point(s).")))
              (princ "\nGenerating 3D pipe...")
              (setq result (gtp:model-corner-route pts dn carrier casing mode style))
              (princ (strcat "\nCreated Isoplus DN" (itoa dn) " Series " (itoa series) " | " flowType " | " (itoa (nth 0 result)) " straight spool(s) | " (itoa (nth 1 result)) " 3D elbow(s)."))
              (if (> (nth 2 result) 0) (princ (strcat "\nNote: " (itoa (nth 2 result)) " elbow fitting leg(s) were shortened for available route length.")))
              (if (and (= (nth 0 result) 0) (= (nth 1 result) 0)) (princ "\nWarning: no pipe solids were generated from this route. Check that the selected route has non-zero length."))
            )
            (princ "\nCould not obtain route vertices.")
          )
        )
        (princ "\nGTPPIPE accepts LINE, LWPOLYLINE or POLYLINE.")
      )
    )
    (princ "\nNothing selected.")
  )
  (setvar "CMDECHO" old) (princ)
)

(defun gtp:last-item (lst) (last lst))
(defun gtp:butlast (lst / out) (setq out '()) (while (cdr lst) (setq out (append out (list (car lst)))) (setq lst (cdr lst))) out)
(defun gtp:replace-first (lst value) (if lst (cons value (cdr lst)) (list value)))
(defun gtp:replace-last (lst value) (if lst (append (gtp:butlast lst) (list value)) (list value)))
(defun gtp:valid-route-p (ent / typ) (if ent (progn (setq typ (cdr (assoc 0 (entget ent)))) (member typ '("LINE" "LWPOLYLINE" "POLYLINE"))) nil))
(defun gtp:end-info (pts pick / p0 pN d0 dN adj dir ordered)
  (setq p0 (car pts) pN (gtp:last-item pts) d0 (distance pick p0) dN (distance pick pN))
  (if (<= d0 dN)
    (progn (setq adj (cadr pts) dir (gtp:vunit (gtp:vsub p0 adj)) ordered (reverse pts)) (list (cons 'end p0) (cons 'dir dir) (cons 'ordered ordered) (cons 'len (distance p0 adj))))
    (progn (setq adj (nth (- (length pts) 2) pts) dir (gtp:vunit (gtp:vsub pN adj)) ordered pts) (list (cons 'end pN) (cons 'dir dir) (cons 'ordered ordered) (cons 'len (distance pN adj))))
  )
)
(defun gtp:line-line-intersection (p1 u p2 v / w a b c d e den s t q1 q2)
  (setq u (gtp:vunit u) v (gtp:vunit v) w (gtp:vsub p1 p2) a (gtp:dot u u) b (gtp:dot u v) c (gtp:dot v v) d (gtp:dot u w) e (gtp:dot v w) den (- (* a c) (* b b)))
  (if (< (abs den) 1e-10) nil
    (progn
      (setq s (/ (- (* b e) (* c d)) den) t (/ (- (* a e) (* b d)) den))
      (setq q1 (gtp:vadd p1 (gtp:vscale u s)) q2 (gtp:vadd p2 (gtp:vscale v t)))
      (list (cons 'corner (mapcar '(lambda (x y) (/ (+ x y) 2.0)) q1 q2)) (cons 'gap (distance q1 q2)))
    )
  )
)
(defun gtp:make-3d-polyline (pts layer / head)
  (setq head (entmakex (list '(0 . "POLYLINE") '(100 . "AcDbEntity") (cons 8 layer) '(100 . "AcDb3dPolyline") (cons 10 '(0.0 0.0 0.0)) '(66 . 1) '(70 . 8))))
  (if head
    (progn
      (foreach p pts (entmakex (list '(0 . "VERTEX") '(100 . "AcDbEntity") (cons 8 layer) '(100 . "AcDbVertex") '(100 . "AcDb3dPolylineVertex") (cons 10 p) '(70 . 32))))
      (entmakex (list '(0 . "SEQEND") '(100 . "AcDbEntity") (cons 8 layer))) head
    )
  )
)
(defun gtp:miter-route-points (info1 info2 corner / a b)
  (setq a (gtp:replace-last (cdr (assoc 'ordered info1)) corner) b (reverse (cdr (assoc 'ordered info2))) b (gtp:replace-first b corner))
  (append a (cdr b))
)
(defun c:GTPMITER (/ *error* old sel1 sel2 ent1 ent2 pick1 pick2 pts1 pts2 info1 info2 ll corner gap tol route newEnt ss ans)
  (vl-load-com)
  (defun *error* (msg) (if old (setvar "CMDECHO" old)) (if (and msg (/= msg "Function cancelled") (/= msg "quit / exit abort")) (princ (strcat "\nGTPMITER error: " msg))) (princ))
  (setq old (getvar "CMDECHO")) (setvar "CMDECHO" 0) (gtp:layers)
  (setq sel1 (entsel "\nSelect FIRST route near the end to connect: "))
  (if sel1
    (progn
      (setq ent1 (car sel1))
      (if (gtp:valid-route-p ent1)
        (progn
          (setq sel2 (entsel "\nSelect SECOND route near the end to connect: "))
          (if (and sel2 (/= ent1 (car sel2)) (gtp:valid-route-p (car sel2)))
            (progn
              (setq ent2 (car sel2) pick1 (trans (cadr sel1) 1 0) pick2 (trans (cadr sel2) 1 0) pts1 (gtp:curve-points ent1) pts2 (gtp:curve-points ent2))
              (if (and pts1 pts2 (>= (length pts1) 2) (>= (length pts2) 2))
                (progn
                  (setq info1 (gtp:end-info pts1 pick1) info2 (gtp:end-info pts2 pick2))
                  (setq ll (gtp:line-line-intersection (cdr (assoc 'end info1)) (cdr (assoc 'dir info1)) (cdr (assoc 'end info2)) (cdr (assoc 'dir info2))))
                  (if ll
                    (progn
                      (setq corner (cdr (assoc 'corner ll)) gap (cdr (assoc 'gap ll)) tol (max 1e-7 (* 0.002 (max (cdr (assoc 'len info1)) (cdr (assoc 'len info2))))))
                      (if (<= gap tol)
                        (progn
                          (setq route (gtp:miter-route-points info1 info2 corner) newEnt (gtp:make-3d-polyline route "GTP-PIPE-CENTRELINE"))
                          (if newEnt
                            (progn
                              (princ (strcat "\nMiter centreline created at (" (rtos (car corner) 2 4) ", " (rtos (cadr corner) 2 4) ", " (rtos (caddr corner) 2 4) ")."))
                              (initget "Keep Delete") (setq ans (getkword "\nSource objects [Keep/Delete] <Keep>: ")) (if (null ans) (setq ans "Keep"))
                              (if (= ans "Delete") (progn (entdel ent1) (entdel ent2)))
                              (setq ss (ssadd)) (ssadd newEnt ss) (sssetfirst nil ss) (princ "\nNew centreline selected. Run GTPPIPE.")
                            )
                            (princ "\nCould not create joined 3D centreline.")
                          )
                        )
                        (princ (strcat "\nThe two selected axes are skew in 3D. Closest gap = " (rtos gap 2 6) "."))
                      )
                    )
                    (princ "\nSelected route ends are parallel/nearly parallel; no miter intersection exists.")
                  )
                )
                (princ "\nCould not read route vertices.")
              )
            )
            (princ "\nSecond selection must be a different LINE/POLYLINE.")
          )
        )
        (princ "\nFirst selection must be a LINE/POLYLINE.")
      )
    )
    (princ "\nNothing selected.")
  )
  (setvar "CMDECHO" old) (princ)
)
(defun c:GTPMITTER () (c:GTPMITER))

; =============================================================================
; MASTER COMPONENT INTEGRATION
; =============================================================================
(setq *gtp-component-next-id* 1)
(setq *gtp-components* '())
(defun gtp:component-get (item key) (cdr (assoc key item)))
(defun gtp:component-make (type system dn series position direction length catalogue options)
  (list (cons 'id *gtp-component-next-id*) (cons 'type type) (cons 'system system) (cons 'dn dn) (cons 'series series) (cons 'position position) (cons 'direction (gtp:vunit direction)) (cons 'length length) (cons 'catalogue catalogue) (cons 'options options))
)
(defun gtp:component-register (comp) (setq *gtp-components* (append *gtp-components* (list comp))) (setq *gtp-component-next-id* (1+ *gtp-component-next-id*)) comp)
(defun gtp:component-find (id / out c) (setq out nil) (foreach c *gtp-components* (if (= (gtp:component-get c 'id) id) (setq out c))) out)
(defun gtp:components-by-type (type / out c) (setq out '()) (foreach c *gtp-components* (if (= (gtp:component-get c 'type) type) (setq out (cons c out)))) (reverse out))
(defun gtp:curve-point-safe (ent pick / r) (setq r (vl-catch-all-apply 'vlax-curve-getClosestPointTo (list ent pick))) (if (vl-catch-all-error-p r) nil r))
(defun gtp:curve-tangent-safe (ent p / par d)
  (setq par (vl-catch-all-apply 'vlax-curve-getParamAtPoint (list ent p)))
  (if (vl-catch-all-error-p par) '(1.0 0.0 0.0)
    (progn
      (setq d (vl-catch-all-apply 'vlax-curve-getFirstDeriv (list ent par)))
      (if (or (vl-catch-all-error-p d) (null d) (< (gtp:vmag d) 1e-12)) '(1.0 0.0 0.0) (gtp:vunit d))
    )
  )
)
(defun gtp:axis-matrix-start (p1 p2 / z ref x y)
  (setq z (gtp:vunit (gtp:vsub p2 p1)))
  (if (> (abs (caddr z)) 0.999) (setq ref '(0.0 1.0 0.0)) (setq ref '(0.0 0.0 1.0)))
  (setq x (gtp:vunit (gtp:cross ref z)) y (gtp:cross z x))
  (list (list (car x) (car y) (car z) (car p1)) (list (cadr x) (cadr y) (cadr z) (cadr p1)) (list (caddr x) (caddr y) (caddr z) (caddr p1)) (list 0.0 0.0 0.0 1.0))
)
(setq *gtp-valve-single-db*
 '((20 "SINGLE2VD" 120.0 260.0 180.0) (25 "SINGLE2VD" 130.0 270.0 190.0) (32 "SINGLE2VD" 140.0 280.0 200.0) (40 "SINGLE2VD" 150.0 300.0 210.0) (50 "SINGLE2VD" 165.0 320.0 220.0) (65 "SINGLE2VD" 180.0 340.0 230.0) (80 "SINGLE2VD" 195.0 360.0 240.0) (100 "SINGLE2VD" 220.0 400.0 260.0) (125 "SINGLE2VD" 250.0 450.0 280.0) (150 "SINGLE2VD" 285.0 500.0 300.0) (200 "SINGLE2VD" 340.0 600.0 340.0) (250 "SINGLE2VD" 400.0 700.0 380.0) (300 "SINGLE2VD" 460.0 800.0 420.0) (350 "SINGLE2VD" 510.0 900.0 460.0) (400 "SINGLE2VD" 570.0 1000.0 500.0) (450 "SINGLE2VD" 630.0 1100.0 540.0) (500 "SINGLE2VD" 700.0 1200.0 580.0) (600 "SINGLE2VD" 820.0 1400.0 640.0)))
(setq *gtp-valve-twin-db*
 '((20 "TWIN2VD" 140.0 330.0 190.0) (25 "TWIN2VD" 150.0 340.0 200.0) (32 "TWIN2VD" 165.0 360.0 210.0) (40 "TWIN2VD" 180.0 380.0 220.0) (50 "TWIN2VD" 195.0 400.0 230.0) (65 "TWIN2VD" 210.0 430.0 240.0) (80 "TWIN2VD" 230.0 460.0 250.0) (100 "TWIN2VD" 260.0 520.0 280.0) (125 "TWIN2VD" 290.0 580.0 300.0) (150 "TWIN2VD" 330.0 640.0 320.0) (200 "TWIN2VD" 390.0 760.0 360.0) (250 "TWIN2VD" 460.0 880.0 400.0) (300 "TWIN2VD" 520.0 1000.0 440.0) (350 "TWIN2VD" 580.0 1120.0 480.0) (400 "TWIN2VD" 650.0 1240.0 520.0) (450 "TWIN2VD" 720.0 1360.0 560.0) (500 "TWIN2VD" 800.0 1480.0 600.0) (600 "TWIN2VD" 930.0 1700.0 660.0)))
(defun gtp:valve-row (dn family) (assoc dn (if (= family "SINGLE2VD") *gtp-valve-single-db* *gtp-valve-twin-db*)))
(defun gtp:valve-family-prompt (/ s) (initget "SINGLE2VD TWIN2VD") (setq s (getkword "\nValve family [SINGLE2VD/TWIN2VD] <SINGLE2VD>: ")) (if s s "SINGLE2VD"))
(defun gtp:make-valve-solid (center tangent bodyOd bodyLen stemH layer / p1 p2 flangeLen f1 f2 sh se obj up)
  (setq p1 (gtp:vadd center (gtp:vscale tangent (- (/ (gtp:mm bodyLen) 2.0)))) p2 (gtp:vadd center (gtp:vscale tangent (/ (gtp:mm bodyLen) 2.0))))
  (setq obj (gtp:make-cylinder p1 p2 (gtp:mm bodyOd) layer) flangeLen (gtp:mm 45.0))
  (setq f1 (gtp:make-cylinder p1 (gtp:vadd p1 (gtp:vscale tangent flangeLen)) (* (gtp:mm bodyOd) 1.14) layer))
  (setq f2 (gtp:make-cylinder (gtp:vadd p2 (gtp:vscale tangent (- flangeLen))) p2 (* (gtp:mm bodyOd) 1.14) layer))
  (if (> (abs (caddr tangent)) 0.95) (setq up '(1.0 0.0 0.0)) (setq up '(0.0 0.0 1.0)))
  (setq sh center se (gtp:vadd center (gtp:vscale up (gtp:mm stemH))))
  (gtp:make-cylinder sh se (max (gtp:mm 35.0) (* (gtp:mm bodyOd) 0.20)) layer)
  (list obj f1 f2)
)
(defun gtp:place-valve (ent pick family dn row / p t bodyOd bodyLen stemH comp)
  (setq p (gtp:curve-point-safe ent pick))
  (if p
    (progn
      (setq t (gtp:curve-tangent-safe ent p) bodyOd (nth 2 row) bodyLen (nth 3 row) stemH (nth 4 row))
      (gtp:make-valve-solid p t bodyOd bodyLen stemH "GTP-PIPE-CASING")
      (setq comp (gtp:component-make "VALVE" *gtp-flow-type* dn 2 p t bodyLen (nth 1 row) (list (cons 'family family) (cons 'footprint (* 0.5 (gtp:mm bodyLen))) (cons 'modelLength (gtp:mm bodyLen)) (cons 'bodyOd (gtp:mm bodyOd)) (cons 'stemHeight (gtp:mm stemH)))))
      (gtp:component-register comp)
    )
  )
)
(defun c:GTPVALVECATALOG (/ family db r)
  (setq family (gtp:valve-family-prompt) db (if (= family "SINGLE2VD") *gtp-valve-single-db* *gtp-valve-twin-db*))
  (princ (strcat "\n" family " reference catalogue:"))
  (foreach r db (princ (strcat "\n  DN" (itoa (nth 0 r)) " | body OD " (rtos (nth 2 r) 2 1) " mm | length " (rtos (nth 3 r) 2 1) " mm | stem " (rtos (nth 4 r) 2 1) " mm")))
  (princ)
)
(defun c:GTPVALVE (/ *error* old sel ent family dn row pick comp)
  (vl-load-com)
  (defun *error* (msg) (if old (setvar "CMDECHO" old)) (if (and msg (/= msg "Function cancelled") (/= msg "quit / exit abort")) (princ (strcat "\nGTPVALVE error: " msg))) (princ))
  (setq old (getvar "CMDECHO")) (setvar "CMDECHO" 0) (gtp:layers) (setq sel (entsel "\nSelect route for valve: "))
  (if sel
    (progn
      (setq ent (car sel))
      (if (gtp:valid-route-p ent)
        (progn
          (setq family (gtp:valve-family-prompt) row nil)
          (while (null row)
            (setq dn (getint "\nValve DN [20/25/32/40/50/65/80/100/125/150/200/250/300/350/400/450/500/600]: "))
            (if dn (setq row (gtp:valve-row dn family)))
            (if (and dn (null row)) (princ "\nDN not in valve reference catalogue."))
          )
          (princ "\nPick valve centre on the route: ") (setq pick (getpoint))
          (if pick
            (progn
              (setq comp (gtp:place-valve ent (trans pick 1 0) family dn row))
              (if comp (princ (strcat "\nValve #" (itoa (gtp:component-get comp 'id)) " placed at route centre. Pipe modelling will leave its footprint free when GTPPIPE is run.")) (princ "\nCould not place valve on selected route."))
            )
            (princ "\nValve placement cancelled.")
          )
        )
        (princ "\nGTPVALVE accepts LINE, LWPOLYLINE or POLYLINE.")
      )
    )
    (princ "\nNothing selected.")
  )
  (setvar "CMDECHO" old) (princ)
)
(defun c:GTPVALVESUMMARY (/ vals c p cat)
  (setq vals (gtp:components-by-type "VALVE"))
  (princ (strcat "\nValve components registered: " (itoa (length vals))))
  (foreach c vals
    (setq p (gtp:component-get c 'position) cat (gtp:component-get c 'catalogue))
    (princ (strcat "\n  #" (itoa (gtp:component-get c 'id)) " " (if cat cat "VALVE") " | DN" (itoa (gtp:component-get c 'dn))))
    (if p (princ (strcat " | (" (rtos (car p) 2 3) ", " (rtos (cadr p) 2 3) ", " (rtos (caddr p) 2 3) ")")))
  )
  (princ)
)
(defun c:GTPCOMPONENTS (/ c p)
  (princ (strcat "\nGTP components registered: " (itoa (length *gtp-components*))))
  (foreach c *gtp-components*
    (setq p (gtp:component-get c 'position))
    (princ (strcat "\n  #" (itoa (gtp:component-get c 'id)) " | " (gtp:component-get c 'type) " | DN" (itoa (gtp:component-get c 'dn))))
    (if p (princ (strcat " | (" (rtos (car p) 2 2) ", " (rtos (cadr p) 2 2) ", " (rtos (caddr p) 2 2) ")")))
  )
  (princ)
)
(defun c:GTPCLEARCOMPONENTS () (setq *gtp-components* '() *gtp-component-next-id* 1) (princ "\nGTP component registry cleared. Existing solids are not deleted.") (princ))
(defun gtp:get-component-route-data (msg / sel ent pick p t row dn series casing carrier)
  (setq sel (entsel msg))
  (if sel
    (progn
      (setq ent (car sel))
      (if (gtp:valid-route-p ent)
        (progn
          (setq pick (getpoint "\nPick component centre on route: "))
          (if pick
            (progn
              (setq p (gtp:curve-point-safe ent (trans pick 1 0)) t (gtp:curve-tangent-safe ent p))
              (gtp:setup-units) (setq row (gtp:get-dn) dn (nth 0 row) series (gtp:get-series) carrier (gtp:mm (nth 1 row)) casing (gtp:mm (gtp:casing-od row series)))
              (list ent p t row dn series carrier casing)
            )
          )
        )
      )
    )
  )
)
(defun c:GTPTEE (/ data ent p t row dn series carrier casing bp bt comp)
  (setq data (gtp:get-component-route-data "\nSelect route for TEE: "))
  (if data
    (progn
      (setq ent (nth 0 data) p (nth 1 data) t (nth 2 data) row (nth 3 data) dn (nth 4 data) series (nth 5 data) carrier (nth 6 data) casing (nth 7 data) bp (getpoint "\nPick branch end point: "))
      (if bp
        (progn
          (setq bp (trans bp 1 0) bt (gtp:vunit (gtp:vsub bp p)))
          (if (< (gtp:vmag bt) 1e-9) (setq bt '(0.0 1.0 0.0)))
          (gtp:make-cylinder (gtp:vadd p (gtp:vscale t (- (* 0.5 carrier)))) (gtp:vadd p (gtp:vscale t (* 0.5 carrier))) casing "GTP-PIPE-CASING")
          (gtp:make-cylinder p bp casing "GTP-PIPE-CASING")
          (setq comp (gtp:component-register (gtp:component-make "TEE" *gtp-flow-type* dn series p t carrier "REFERENCE-TEE" (list (cons 'branchDirection bt) (cons 'branchEnd bp)))))
          (princ (strcat "\nTEE #" (itoa (gtp:component-get comp 'id)) " placed."))
        )
        (princ "\nTEE placement cancelled.")
      )
    )
    (princ "\nTEE placement cancelled.")
  )
  (princ)
)
(defun c:GTPBRANCH (/ data p bp bt row dn series carrier casing comp)
  (setq data (gtp:get-component-route-data "\nSelect route for BRANCH: "))
  (if data
    (progn
      (setq p (nth 1 data) row (nth 3 data) dn (nth 4 data) series (nth 5 data) carrier (nth 6 data) casing (nth 7 data) bp (getpoint "\nPick branch end point: "))
      (if bp
        (progn
          (setq bp (trans bp 1 0) bt (gtp:vunit (gtp:vsub bp p)))
          (gtp:make-cylinder p bp casing "GTP-PIPE-CASING")
          (setq comp (gtp:component-register (gtp:component-make "BRANCH" *gtp-flow-type* dn series p bt carrier "REFERENCE-BRANCH" (list (cons 'branchEnd bp)))))
          (princ (strcat "\nBRANCH #" (itoa (gtp:component-get comp 'id)) " placed."))
        )
        (princ "\nBRANCH placement cancelled.")
      )
    )
    (princ "\nBRANCH placement cancelled.")
  )
  (princ)
)
(defun c:GTPREDUCER (/ data p t row dn series casing carrier newDn newRow newCasing len p1 p2 doc ms sol comp)
  (setq data (gtp:get-component-route-data "\nSelect route for REDUCER: "))
  (if data
    (progn
      (setq p (nth 1 data) t (nth 2 data) row (nth 3 data) dn (nth 4 data) series (nth 5 data) casing (nth 7 data))
      (setq newDn (getint "\nReducer other DN: ") newRow (if newDn (gtp:find-dn newDn)))
      (if newRow
        (progn
          (setq newCasing (gtp:mm (gtp:casing-od newRow series)) len (gtp:mm 300.0) p1 (gtp:vadd p (gtp:vscale t (- (/ len 2.0)))) p2 (gtp:vadd p (gtp:vscale t (/ len 2.0))))
          (setq doc (vla-get-ActiveDocument (vlax-get-acad-object)) ms (vla-get-ModelSpace doc) sol (vl-catch-all-apply 'vla-AddCone (list ms (/ casing 2.0) len (/ newCasing 2.0))))
          (if (and sol (not (vl-catch-all-error-p sol)))
            (progn (vla-TransformBy sol (vlax-tmatrix (gtp:axis-matrix-start p1 p2))) (vla-put-Layer sol "GTP-PIPE-CASING") (vla-put-Color sol *gtp-pipe-color*))
            (gtp:make-cylinder p1 p2 (max casing newCasing) "GTP-PIPE-CASING")
          )
          (setq comp (gtp:component-register (gtp:component-make "REDUCER" *gtp-flow-type* dn series p t len "REFERENCE-REDUCER" (list (cons 'otherDN newDn) (cons 'otherCasing newCasing)))))
          (princ (strcat "\nREDUCER #" (itoa (gtp:component-get comp 'id)) " placed DN" (itoa dn) " -> DN" (itoa newDn) "."))
        )
        (princ "\nReducer DN not in current database.")
      )
    )
    (princ "\nREDUCER placement cancelled.")
  )
  (princ)
)
(defun c:GTPENDCAP (/ *error* old sel ent pick pts p endp prev dir row dn series casing capLen comp)
  (defun *error* (msg) (if old (setvar "CMDECHO" old)) (if (and msg (/= msg "Function cancelled") (/= msg "quit / exit abort")) (princ (strcat "\nGTPENDCAP error: " msg))) (princ))
  (setq old (getvar "CMDECHO")) (setvar "CMDECHO" 0) (gtp:layers) (setq sel (entsel "\nSelect route for ENDCAP: "))
  (if sel
    (progn
      (setq ent (car sel) pick (trans (cadr sel) 1 0))
      (if (gtp:valid-route-p ent)
        (progn
          (setq pts (gtp:curve-points ent))
          (if (and pts (>= (length pts) 2))
            (progn
              (setq p (car pts) endp (nth (1- (length pts)) pts))
              (if (> (distance pick endp) (distance pick p)) (progn (setq p endp) (setq prev (nth (- (length pts) 2) pts))) (setq prev (cadr pts)))
              (setq dir (gtp:vunit (gtp:vsub p prev)))
              (gtp:setup-units) (setq row (gtp:get-dn) dn (nth 0 row) series (gtp:get-series) casing (gtp:mm (gtp:casing-od row series)) capLen (gtp:mm 90.0))
              (gtp:make-cylinder (gtp:vadd p (gtp:vscale dir (- capLen))) p casing "GTP-PIPE-CASING")
              (setq comp (gtp:component-register (gtp:component-make "END_CAP" *gtp-flow-type* dn series p dir capLen "REFERENCE-ENDCAP" nil)))
              (princ (strcat "\nENDCAP #" (itoa (gtp:component-get comp 'id)) " placed at selected route end."))
            )
            (princ "\nCould not read route endpoints.")
          )
        )
        (princ "\nGTPENDCAP accepts LINE, LWPOLYLINE or POLYLINE.")
      )
    )
    (princ "\nNothing selected.")
  )
  (setvar "CMDECHO" old) (princ)
)
(defun gtp:valve-components-on-segment (a b / vals out c p d proj foot)
  (setq vals (gtp:components-by-type "VALVE") out '())
  (foreach c vals
    (setq p (gtp:component-get c 'position) d (gtp:vunit (gtp:vsub b a)) proj (gtp:dot (gtp:vsub p a) d))
    (if (and (> proj 0.0) (< proj (distance a b)))
      (progn
        (setq foot (gtp:component-get (gtp:component-get c 'options) 'footprint))
        (if (or (null foot) (<= foot 0.0)) (setq foot 0.0))
        (setq out (cons (list proj foot c) out))
      )
    )
  )
  (vl-sort out '(lambda (x y) (< (car x) (car y))))
)
(defun gtp:model-segment-valve-aware (p1 p2 carrier casing mode / len d item proj foot count ordered start cutStart cutEnd)
  (setq len (distance p1 p2) d (gtp:vunit (gtp:vsub p2 p1)) ordered (gtp:valve-components-on-segment p1 p2) start 0.0 count 0)
  (foreach item ordered
    (setq proj (car item) foot (cadr item) cutStart (max start (- proj foot)) cutEnd (min len (+ proj foot)))
    (if (> (- cutStart start) 1e-8) (setq count (+ count (gtp:model-segment (gtp:vadd p1 (gtp:vscale d start)) (gtp:vadd p1 (gtp:vscale d cutStart)) carrier casing mode))))
    (setq start (max start cutEnd))
  )
  (if (< start len) (setq count (+ count (gtp:model-segment (gtp:vadd p1 (gtp:vscale d start)) p2 carrier casing mode))))
  count
)
(defun gtp:model-corner-route-component-aware (pts dn carrier casing mode style / n elbows i spec p1 p2 s e spoolCount elbowCount clippedCount)
  (setq n (length pts) elbows '() i 0 spoolCount 0 elbowCount 0 clippedCount 0)
  (while (< i n)
    (setq spec nil)
    (if (and (> i 0) (< i (1- n))) (setq spec (gtp:make-elbow-spec (nth (1- i) pts) (nth i pts) (nth (1+ i) pts) dn carrier casing style)))
    (if (and spec (gtp:spec 'clipped spec)) (setq clippedCount (1+ clippedCount)))
    (setq elbows (append elbows (list spec)) i (1+ i))
  )
  (setq i 0)
  (while (< i (1- n))
    (setq p1 (nth i pts) p2 (nth (1+ i) pts) s (if (nth i elbows) (gtp:spec 'end (nth i elbows)) p1) e (if (nth (1+ i) elbows) (gtp:spec 'start (nth (1+ i) elbows)) p2))
    (if (> (distance s e) 1e-8) (setq spoolCount (+ spoolCount (gtp:model-segment-valve-aware s e carrier casing mode))))
    (setq i (1+ i))
  )
  (setq i 1)
  (while (< i (1- n))
    (if (nth i elbows) (progn (gtp:model-elbow (nth i elbows) carrier casing mode) (setq elbowCount (1+ elbowCount))))
    (setq i (1+ i))
  )
  (list spoolCount elbowCount clippedCount)
)
(setq *gtp-model-corner-route-component-aware* T)
(defun gtp:model-corner-route (pts dn carrier casing mode style) (gtp:model-corner-route-component-aware pts dn carrier casing mode style))

(defun c:GTPTEST (/ checks ok item name fn)
  (setq checks (list (list "GTPPIPE" 'c:GTPPIPE) (list "GTPMITER" 'c:GTPMITER) (list "GTPMITTER" 'c:GTPMITTER) (list "GTPUNITS" 'c:GTPUNITS) (list "GTPLAYER" 'c:GTPLAYER) (list "GTPVALVE" 'c:GTPVALVE) (list "GTPVALVECATALOG" 'c:GTPVALVECATALOG) (list "GTPVALVESUMMARY" 'c:GTPVALVESUMMARY) (list "GTPTEE" 'c:GTPTEE) (list "GTPBRANCH" 'c:GTPBRANCH) (list "GTPREDUCER" 'c:GTPREDUCER) (list "GTPENDCAP" 'c:GTPENDCAP) (list "GTPCOMPONENTS" 'c:GTPCOMPONENTS) (list "GTPCLEARCOMPONENTS" 'c:GTPCLEARCOMPONENTS) (list "GTPHELP" 'c:GTPHELP)))
  (setq ok T)
  (princ "\n========================================")
  (princ "\n GTP MASTER LOAD/SYNTAX TEST")
  (princ "\n========================================")
  (foreach item checks
    (setq name (car item) fn (cadr item))
    (if (fboundp fn) (princ (strcat "\n[OK] " name)) (progn (setq ok nil) (princ (strcat "\n[FAIL] " name))))
  )
  (princ (strcat "\nComponents in memory: " (itoa (length *gtp-components*))))
  (if (fboundp 'gtp:model-corner-route) (princ "\n[OK] Valve-aware route model registered.") (progn (setq ok nil) (princ "\n[FAIL] Route model missing.")))
  (if ok (princ "\nGTPTEST PASS - command functions are loaded in the master file.") (princ "\nGTPTEST FAIL - see the [FAIL] line(s) above."))
  (princ)
)
(defun c:GTPHELP ()
  (princ "\nGTP commands loaded in GTP_DH_TOOLKIT.lsp:")
  (princ "\n  GTPPIPE             Pipe + elbow route modelling")
  (princ "\n  GTPMITER            Join two route ends at axis intersection")
  (princ "\n  GTPMITTER           Alias for GTPMITER")
  (princ "\n  GTPUNITS            Set/check drawing-unit scale")
  (princ "\n  GTPLAYER            Create/check GTP layers")
  (princ "\n  GTPVALVE            Place a centre-based valve component")
  (princ "\n  GTPVALVECATALOG     Show valve reference catalogue")
  (princ "\n  GTPVALVESUMMARY     List registered valves")
  (princ "\n  GTPTEE              Place reference tee component")
  (princ "\n  GTPBRANCH           Place reference branch component")
  (princ "\n  GTPREDUCER          Place reference reducer component")
  (princ "\n  GTPENDCAP           Place reference end-cap component")
  (princ "\n  GTPCOMPONENTS       List registered components")
  (princ "\n  GTPCLEARCOMPONENTS  Clear in-memory component registry")
  (princ "\n  GTPTEST             Master load/syntax command-function test")
  (princ)
)
(princ "\nGTP_DH_TOOLKIT.lsp loaded successfully.")
(princ "\nCommands: GTPPIPE, GTPMITER, GTPMITTER, GTPUNITS, GTPLAYER, GTPVALVE, GTPVALVECATALOG, GTPVALVESUMMARY, GTPTEE, GTPBRANCH, GTPREDUCER, GTPENDCAP, GTPCOMPONENTS, GTPCLEARCOMPONENTS, GTPTEST, GTPHELP.")
(princ)
