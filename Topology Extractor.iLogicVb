AddReference "System.Windows.Forms"

Imports System
Imports System.Text
Imports System.Text.RegularExpressions
Imports System.Collections.Generic
Imports System.Globalization
Imports System.Windows.Forms


Sub Main()

    ' =================================================================
    ' AUTOSPOOL - SINGLE SPOOL TOPOLOGY / DIMENSION VERIFIER V0.4
    '
    ' GOAL
    ' ----
    ' Work on ONE active spool IAM until the extracted schematic and
    ' dimensions are trustworthy.
    '
    ' OUTPUTS
    ' -------
    '   _AutoSpoolSingle\<Assembly>_VERIFY.svg
    '   _AutoSpoolSingle\<Assembly>_DATA.csv
    '
    ' IMPORTANT IDEA
    ' --------------
    ' Connection geometry and manufacturing dimension geometry are
    ' deliberately separated.
    '
    ' For a flange:
    '   - nearest suitable circular planar face = connection helper only
    '   - outermost flange face in the outward spool direction =
    '       schematic / manufacturing reference
    '
    ' The schematic is NOT a generic graph.  It is built from an
    ' extracted manufacturing centerline skeleton:
    '
    '   FLANGE : host port -> outer flange face
    '   PIPE   : port -> port
    '   TEE    : center -> each port
    '   ELBOW  : true quarter-arc between ports, with center reference
    '
    ' Straight collinear primitive segments are automatically grouped
    ' into runs.  This is what produces useful overall dimensions such
    ' as:
    '
    '   flange + pipe + tee + elbow tangent = overall straight run
    '
    ' =================================================================


    If ThisApplication.ActiveDocument Is Nothing Then

        MessageBox.Show( _
            "No active Inventor document.", _
            "AutoSpool V0.4")

        Exit Sub

    End If


    If ThisApplication.ActiveDocument.DocumentType <> _
       DocumentTypeEnum.kAssemblyDocumentObject Then

        MessageBox.Show( _
            "Open ONE spool .IAM and run this rule again.", _
            "AutoSpool V0.4")

        Exit Sub

    End If


    Dim asmDoc As AssemblyDocument = _
        CType(ThisApplication.ActiveDocument, AssemblyDocument)


    If String.IsNullOrWhiteSpace(asmDoc.FullFileName) Then

        MessageBox.Show( _
            "Please save the spool assembly before running the verifier.", _
            "AutoSpool V0.4")

        Exit Sub

    End If


    Dim asmName As String = _
        System.IO.Path.GetFileNameWithoutExtension(asmDoc.FullFileName)

    Dim asmFolder As String = _
        System.IO.Path.GetDirectoryName(asmDoc.FullFileName)

    Dim outputFolder As String = _
        System.IO.Path.Combine(asmFolder, "_AutoSpoolSingle")


    System.IO.Directory.CreateDirectory(outputFolder)


    Dim csvFile As String = _
        System.IO.Path.Combine( _
            outputFolder, _
            SafeFileName(asmName) & "_DATA.csv")

    Dim svgFile As String = _
        System.IO.Path.Combine( _
            outputFolder, _
            SafeFileName(asmName) & "_VERIFY.svg")


    Try

        ' =============================================================
        ' 1. READ COMPONENTS / PORT CANDIDATES
        ' =============================================================

        Dim nodes As List(Of NodeRecord) = _
            ScanAssembly(asmDoc)


        AssignDisplayCodes(nodes)


        ' =============================================================
        ' 2. DETECT COMPONENT CONNECTIONS
        ' =============================================================

        Dim edges As List(Of EdgeRecord) = _
            DetectConnections(nodes)


        ' =============================================================
        ' 3. CALCULATE ELBOW / TEE / FLANGE REFERENCE POINTS
        ' =============================================================

        ComputeReferencePoints(nodes, edges)


        ' =============================================================
        ' 4. BUILD TRUE MANUFACTURING SKELETON
        ' =============================================================

        Dim primitives As List(Of PrimitiveSegment) = _
            BuildManufacturingPrimitives(nodes, edges)


        ' =============================================================
        ' 5. COMPONENT-LEVEL DIMENSIONS
        ' =============================================================

        Dim componentDimensions As List(Of DimensionRecord) = _
            BuildComponentDimensions(nodes, edges)


        ' =============================================================
        ' 6. FIND MAXIMAL STRAIGHT RUNS
        '
        ' Example:
        '
        ' outer flange -> flange thickness -> pipe -> tee run ->
        ' elbow tangent center
        '
        ' all become ONE straight overall chain.
        ' =============================================================

        Dim chains As List(Of StraightChain) = _
            BuildStraightChains(primitives)


        Dim overallDimensions As List(Of DimensionRecord) = _
            BuildOverallDimensions(chains)


        AssignDimensionsToChains( _
            componentDimensions, _
            chains)


        ' =============================================================
        ' 7. GRAPH DIAGNOSTICS
        ' =============================================================

        Dim graphGroups As Integer = _
            CountGraphGroups(nodes)

        Dim unresolved As New List(Of String)


        For Each n As NodeRecord In nodes

            If n.Neighbours.Count = 0 Then
                unresolved.Add(n.Code)
            End If

        Next


        ' =============================================================
        ' 8. WRITE COMPLETE CSV
        ' =============================================================

        WriteCompleteCsv( _
            asmName, _
            nodes, _
            edges, _
            primitives, _
            componentDimensions, _
            chains, _
            overallDimensions, _
            graphGroups, _
            unresolved, _
            csvFile)


        ' =============================================================
        ' 9. GENERATE CLEAN VISUAL SCHEMATIC
        ' =============================================================

        GenerateVerificationSvg( _
            asmName, _
            nodes, _
            edges, _
            primitives, _
            componentDimensions, _
            chains, _
            overallDimensions, _
            graphGroups, _
            unresolved, _
            svgFile)


        ' =============================================================
        ' 10. SUMMARY
        ' =============================================================

        Dim summary As New StringBuilder

        summary.AppendLine("AutoSpool verification complete.")
        summary.AppendLine()
        summary.AppendLine("Components: " & nodes.Count.ToString())
        summary.AppendLine("Connections: " & edges.Count.ToString())
        summary.AppendLine("Graph groups: " & graphGroups.ToString())

        If unresolved.Count > 0 Then

            summary.AppendLine( _
                "Unresolved: " & _
                String.Join(", ", unresolved.ToArray()))

        Else

            summary.AppendLine("Unresolved: none")

        End If


        summary.AppendLine()
        summary.AppendLine("Extracted component dimensions:")


        For Each d As DimensionRecord In componentDimensions

            summary.AppendLine( _
                "  " & _
                d.Label & _
                " = " & _
                FormatMm(d.Value))

        Next


        summary.AppendLine()
        summary.AppendLine("Extracted overall straight runs:")


        For Each d As DimensionRecord In overallDimensions

            summary.AppendLine( _
                "  " & _
                d.Label & _
                " = " & _
                FormatMm(d.Value))

        Next


        summary.AppendLine()
        summary.AppendLine("Output folder:")
        summary.AppendLine(outputFolder)


        MessageBox.Show( _
            summary.ToString(), _
            "AutoSpool V0.4")


        Try

            System.Diagnostics.Process.Start(svgFile)

        Catch

            System.Diagnostics.Process.Start( _
                "explorer.exe", _
                outputFolder)

        End Try


    Catch ex As Exception

        MessageBox.Show( _
            "AutoSpool V0.4 failed:" & vbCrLf & vbCrLf & _
            ex.Message, _
            "AutoSpool V0.4")

        Logger.Error(ex.ToString())

    End Try

End Sub



' ===================================================================
' SCAN ASSEMBLY
' ===================================================================

Function ScanAssembly( _
    asmDoc As AssemblyDocument) As List(Of NodeRecord)


    Dim result As New List(Of NodeRecord)

    Dim occurrences As ComponentOccurrencesEnumerator = _
        asmDoc.ComponentDefinition.Occurrences.AllLeafOccurrences


    For Each occ As ComponentOccurrence In occurrences

        Try

            If occ.Suppressed Then
                Continue For
            End If


            Dim node As New NodeRecord

            node.OccurrenceName = occ.Name


            Dim refDoc As Document = Nothing


            Try
                refDoc = occ.Definition.Document
            Catch
            End Try


            If refDoc IsNot Nothing Then

                node.PartNumber = _
                    GetIProperty( _
                        refDoc, _
                        "Design Tracking Properties", _
                        "Part Number")

                node.Description = _
                    GetIProperty( _
                        refDoc, _
                        "Design Tracking Properties", _
                        "Description")

            End If


            node.ComponentType = _
                GuessComponentType( _
                    node.PartNumber, _
                    node.Description, _
                    node.OccurrenceName)


            ' -------------------------------------------------------
            ' Occurrence center.
            ' Inventor database geometry length = cm.
            ' Convert to mm.
            ' -------------------------------------------------------

            Dim rb As Box = occ.RangeBox


            node.X = _
                ((rb.MinPoint.X + rb.MaxPoint.X) / 2.0) * 10.0

            node.Y = _
                ((rb.MinPoint.Y + rb.MaxPoint.Y) / 2.0) * 10.0

            node.Z = _
                ((rb.MinPoint.Z + rb.MaxPoint.Z) / 2.0) * 10.0


            ' -------------------------------------------------------
            ' Candidate piping ports:
            ' planar face + circular boundary
            ' -------------------------------------------------------

            Dim faceCounter As Integer = 0


            For Each body As SurfaceBody In occ.SurfaceBodies

                For Each face As Face In body.Faces

                    faceCounter += 1


                    If face.SurfaceType <> _
                       SurfaceTypeEnum.kPlaneSurface Then

                        Continue For
                    End If


                    Dim biggestCircle As Inventor.Circle = Nothing
                    Dim circularEdgeCount As Integer = 0


                    For Each edge As Edge In face.Edges

                        Try

                            If edge.GeometryType = _
                               CurveTypeEnum.kCircleCurve Then


                                circularEdgeCount += 1


                                Dim circle As Inventor.Circle = _
                                    CType( _
                                        edge.Geometry, _
                                        Inventor.Circle)


                                If biggestCircle Is Nothing Then

                                    biggestCircle = circle

                                ElseIf circle.Radius > _
                                       biggestCircle.Radius Then

                                    biggestCircle = circle

                                End If

                            End If

                        Catch
                        End Try

                    Next


                    If biggestCircle Is Nothing Then
                        Continue For
                    End If


                    Dim plane As Inventor.Plane = Nothing


                    Try

                        plane = _
                            CType( _
                                face.Geometry, _
                                Inventor.Plane)

                    Catch

                        Continue For

                    End Try


                    Dim p As New PortRecord

                    p.Owner = node
                    p.FaceIndex = faceCounter

                    p.X = biggestCircle.Center.X * 10.0
                    p.Y = biggestCircle.Center.Y * 10.0
                    p.Z = biggestCircle.Center.Z * 10.0

                    p.NX = plane.Normal.X
                    p.NY = plane.Normal.Y
                    p.NZ = plane.Normal.Z


                    Try

                        If face.IsParamReversed Then

                            p.NX *= -1.0
                            p.NY *= -1.0
                            p.NZ *= -1.0

                        End If

                    Catch
                    End Try


                    p.Radius = biggestCircle.Radius * 10.0
                    p.CircularEdges = circularEdgeCount


                    Try

                        p.FaceArea = _
                            face.Evaluator.Area * 100.0

                    Catch

                        p.FaceArea = 0

                    End Try


                    AddPortIfUnique(node.Ports, p)

                Next

            Next


            result.Add(node)


        Catch ex As Exception

            Logger.Error( _
                "Component scan error: " & _
                occ.Name & _
                " : " & _
                ex.Message)

        End Try

    Next


    Return result

End Function



' ===================================================================
' CONNECTION DETECTION
' ===================================================================

Function DetectConnections( _
    nodes As List(Of NodeRecord)) As List(Of EdgeRecord)


    Dim directTolerance As Double = 1.0
    Dim flangeSearchDistance As Double = 60.0
    Dim lateralTolerance As Double = 2.0
    Dim minimumNormalAlignment As Double = 0.90


    Dim result As New List(Of EdgeRecord)

    Dim nonFlangePorts As New List(Of PortRecord)


    For Each n As NodeRecord In nodes

        If n.ComponentType <> "FLANGE" Then

            For Each p As PortRecord In n.Ports
                nonFlangePorts.Add(p)
            Next

        End If

    Next


    ' ===============================================================
    ' PASS 1 - DIRECT PORT TO PORT
    ' ===============================================================

    For i As Integer = 0 To nonFlangePorts.Count - 1

        For j As Integer = i + 1 To nonFlangePorts.Count - 1


            Dim a As PortRecord = _
                nonFlangePorts.Item(i)

            Dim b As PortRecord = _
                nonFlangePorts.Item(j)


            If a.Owner Is b.Owner Then
                Continue For
            End If


            If HasConnection( _
                result, _
                a.Owner, _
                b.Owner) Then

                Continue For
            End If


            Dim portDistance As Double = _
                Dist3D( _
                    a.X, a.Y, a.Z, _
                    b.X, b.Y, b.Z)


            If portDistance > directTolerance Then
                Continue For
            End If


            Dim normalDotValue As Double = _
                NormalDot(a, b)


            If normalDotValue > -minimumNormalAlignment Then
                Continue For
            End If


            AddConnection( _
                result, _
                a, _
                b, _
                "DIRECT", _
                portDistance)

        Next

    Next


    ' ===============================================================
    ' PASS 2 - FLANGE ASSOCIATION
    '
    ' The nearest flange candidate is ONLY used to associate the
    ' flange with the host port.
    '
    ' We then separately calculate the true OUTER flange face.
    ' ===============================================================

    For Each hostNode As NodeRecord In nodes


        If hostNode.ComponentType = "FLANGE" Then
            Continue For
        End If


        For Each hostPort As PortRecord In hostNode.Ports


            If hostPort.Used Then
                Continue For
            End If


            Dim bestFlange As NodeRecord = Nothing
            Dim bestFlangePort As PortRecord = Nothing
            Dim bestScore As Double = Double.MaxValue


            For Each flangeNode As NodeRecord In nodes


                If flangeNode.ComponentType <> "FLANGE" Then
                    Continue For
                End If


                If flangeNode.Neighbours.Count > 0 Then
                    Continue For
                End If


                For Each flangePort As PortRecord In flangeNode.Ports


                    Dim dx As Double = _
                        flangePort.X - hostPort.X

                    Dim dy As Double = _
                        flangePort.Y - hostPort.Y

                    Dim dz As Double = _
                        flangePort.Z - hostPort.Z


                    Dim totalDistance As Double = _
                        Math.Sqrt( _
                            dx * dx + _
                            dy * dy + _
                            dz * dz)


                    If totalDistance > flangeSearchDistance Then
                        Continue For
                    End If


                    Dim axialDistance As Double = _
                        Math.Abs( _
                            dx * hostPort.NX + _
                            dy * hostPort.NY + _
                            dz * hostPort.NZ)


                    Dim lateralSquared As Double = _
                        totalDistance * totalDistance - _
                        axialDistance * axialDistance


                    If lateralSquared < 0 Then
                        lateralSquared = 0
                    End If


                    Dim lateralDistance As Double = _
                        Math.Sqrt(lateralSquared)


                    If lateralDistance > lateralTolerance Then
                        Continue For
                    End If


                    Dim alignment As Double = _
                        Math.Abs( _
                            NormalDot( _
                                hostPort, _
                                flangePort))


                    If alignment < minimumNormalAlignment Then
                        Continue For
                    End If


                    Dim score As Double = _
                        totalDistance + _
                        lateralDistance * 10.0 + _
                        (1.0 - alignment) * 100.0


                    If score < bestScore Then

                        bestScore = score
                        bestFlange = flangeNode
                        bestFlangePort = flangePort

                    End If

                Next

            Next


            If bestFlange IsNot Nothing AndAlso _
               bestFlangePort IsNot Nothing Then


                Dim connectionDistance As Double = _
                    Dist3D( _
                        hostPort.X, _
                        hostPort.Y, _
                        hostPort.Z, _
                        bestFlangePort.X, _
                        bestFlangePort.Y, _
                        bestFlangePort.Z)


                AddConnection( _
                    result, _
                    hostPort, _
                    bestFlangePort, _
                    "FLANGED_END", _
                    connectionDistance)


                ' ---------------------------------------------------
                ' CRITICAL FIX:
                '
                ' Determine flange OUTWARD direction from the host
                ' occurrence toward the flange occurrence, then choose
                ' the farthest coaxial flange face in that direction.
                '
                ' This correctly selects e.g. the 15 mm outer face,
                ' instead of the misleading nearest 5 mm internal face.
                ' ---------------------------------------------------

                FindFlangeOuterAnchor( _
                    bestFlange, _
                    hostNode, _
                    hostPort, _
                    bestFlangePort)

            End If

        Next

    Next


    Return result

End Function



' ===================================================================
' CORRECT FLANGE OUTER FACE
' ===================================================================

Sub FindFlangeOuterAnchor( _
    flange As NodeRecord, _
    hostNode As NodeRecord, _
    hostPort As PortRecord, _
    connectionFace As PortRecord)


    ' ---------------------------------------------------------------
    ' Host port axis.
    ' ---------------------------------------------------------------

    Dim ax As Double = hostPort.NX
    Dim ay As Double = hostPort.NY
    Dim az As Double = hostPort.NZ


    Dim axisLength As Double = _
        Math.Sqrt( _
            ax * ax + _
            ay * ay + _
            az * az)


    If axisLength < 0.000001 Then
        Exit Sub
    End If


    ax /= axisLength
    ay /= axisLength
    az /= axisLength


    ' ---------------------------------------------------------------
    ' Decide which sign of the host axis points outward into flange.
    '
    ' Use HOST OCCURRENCE CENTER -> FLANGE OCCURRENCE CENTER.
    '
    ' This is the key correction.
    ' ---------------------------------------------------------------

    Dim hfx As Double = flange.X - hostNode.X
    Dim hfy As Double = flange.Y - hostNode.Y
    Dim hfz As Double = flange.Z - hostNode.Z


    Dim outwardDot As Double = _
        hfx * ax + _
        hfy * ay + _
        hfz * az


    If outwardDot < 0 Then

        ax *= -1.0
        ay *= -1.0
        az *= -1.0

    End If


    Dim bestPort As PortRecord = Nothing
    Dim bestSignedDistance As Double = Double.MinValue


    For Each candidate As PortRecord In flange.Ports


        ' Same flange axis.
        Dim alignment As Double = _
            Math.Abs( _
                candidate.NX * ax + _
                candidate.NY * ay + _
                candidate.NZ * az)


        If alignment < 0.90 Then
            Continue For
        End If


        Dim dx As Double = candidate.X - hostPort.X
        Dim dy As Double = candidate.Y - hostPort.Y
        Dim dz As Double = candidate.Z - hostPort.Z


        Dim signedDistance As Double = _
            dx * ax + _
            dy * ay + _
            dz * az


        ' Must be on outward side, allowing tiny modelling noise.
        If signedDistance < -1.0 Then
            Continue For
        End If


        Dim totalSquared As Double = _
            dx * dx + _
            dy * dy + _
            dz * dz

        Dim lateralSquared As Double = _
            totalSquared - _
            signedDistance * signedDistance


        If lateralSquared < 0 Then
            lateralSquared = 0
        End If


        Dim lateralDistance As Double = _
            Math.Sqrt(lateralSquared)


        If lateralDistance > 2.5 Then
            Continue For
        End If


        If signedDistance > bestSignedDistance Then

            bestSignedDistance = signedDistance
            bestPort = candidate

        End If

    Next


    If bestPort Is Nothing Then
        bestPort = connectionFace
    End If


    flange.HasOuterAnchor = True

    flange.InnerFaceIndex = connectionFace.FaceIndex
    flange.OuterFaceIndex = bestPort.FaceIndex

    flange.OuterX = bestPort.X
    flange.OuterY = bestPort.Y
    flange.OuterZ = bestPort.Z

    flange.OuterOffset = _
        Dist3D( _
            hostPort.X, hostPort.Y, hostPort.Z, _
            bestPort.X, bestPort.Y, bestPort.Z)


    flange.FlangeHostCode = hostNode.Code

    flange.HostPortX = hostPort.X
    flange.HostPortY = hostPort.Y
    flange.HostPortZ = hostPort.Z

End Sub



' ===================================================================
' ADD CONNECTION
' ===================================================================

Sub AddConnection( _
    edges As List(Of EdgeRecord), _
    portA As PortRecord, _
    portB As PortRecord, _
    connectionType As String, _
    connectionDistance As Double)


    If HasConnection( _
        edges, _
        portA.Owner, _
        portB.Owner) Then

        Exit Sub
    End If


    Dim e As New EdgeRecord

    e.A = portA.Owner
    e.B = portB.Owner

    e.PortA = portA
    e.PortB = portB

    e.ConnectionType = connectionType
    e.ConnectionDistance = connectionDistance


    edges.Add(e)


    portA.Owner.Neighbours.Add(portB.Owner)
    portB.Owner.Neighbours.Add(portA.Owner)

    portA.Used = True
    portB.Used = True

End Sub



' ===================================================================
' REFERENCE POINTS
' ===================================================================

Sub ComputeReferencePoints( _
    nodes As List(Of NodeRecord), _
    edges As List(Of EdgeRecord))


    For Each n As NodeRecord In nodes


        If n.ComponentType = "FLANGE" AndAlso _
           n.HasOuterAnchor Then

            n.RefX = n.OuterX
            n.RefY = n.OuterY
            n.RefZ = n.OuterZ

            n.ReferenceType = "FLANGE_OUTER_FACE"

            Continue For
        End If


        Dim activePorts As List(Of PortRecord) = _
            GetUsedPorts(n, edges)


        ' -----------------------------------------------------------
        ' ELBOW center = intersection of its two connection axes.
        ' -----------------------------------------------------------

        If n.ComponentType = "ELBOW" AndAlso _
           activePorts.Count >= 2 Then


            Dim p1 As PortRecord = activePorts.Item(0)
            Dim p2 As PortRecord = activePorts.Item(1)


            Dim ix As Double = 0
            Dim iy As Double = 0
            Dim iz As Double = 0
            Dim separation As Double = 0


            If ClosestAxisIntersection( _
                p1, _
                p2, _
                ix, iy, iz, _
                separation) Then


                If separation <= 3.0 Then

                    n.RefX = ix
                    n.RefY = iy
                    n.RefZ = iz

                    n.ReferenceType = "ELBOW_CENTER"

                    Continue For

                End If

            End If

        End If


        ' -----------------------------------------------------------
        ' TEE center.
        '
        ' Identify the most-opposed port pair as run ports.
        ' The remaining non-collinear port is branch.
        ' -----------------------------------------------------------

        If n.ComponentType = "TEE" AndAlso _
           activePorts.Count >= 3 Then


            Dim runA As PortRecord = Nothing
            Dim runB As PortRecord = Nothing

            FindMostOpposedPortPair( _
                activePorts, _
                runA, _
                runB)


            Dim branchPort As PortRecord = Nothing


            For Each p As PortRecord In activePorts

                If p Is runA OrElse p Is runB Then
                    Continue For
                End If

                branchPort = p
                Exit For

            Next


            If runA IsNot Nothing AndAlso _
               branchPort IsNot Nothing Then


                Dim ix As Double = 0
                Dim iy As Double = 0
                Dim iz As Double = 0
                Dim separation As Double = 0


                If ClosestAxisIntersection( _
                    runA, _
                    branchPort, _
                    ix, iy, iz, _
                    separation) Then


                    If separation <= 3.0 Then

                        n.RefX = ix
                        n.RefY = iy
                        n.RefZ = iz

                        n.ReferenceType = "TEE_CENTER"

                        Continue For

                    End If

                End If

            End If


            ' Fallback for equal tee:
            ' midpoint of opposed run faces.
            If runA IsNot Nothing AndAlso _
               runB IsNot Nothing Then


                n.RefX = (runA.X + runB.X) / 2.0
                n.RefY = (runA.Y + runB.Y) / 2.0
                n.RefZ = (runA.Z + runB.Z) / 2.0

                n.ReferenceType = "TEE_CENTER_MIDPOINT"

                Continue For

            End If

        End If


        ' -----------------------------------------------------------
        ' Fallback.
        ' -----------------------------------------------------------

        n.RefX = n.X
        n.RefY = n.Y
        n.RefZ = n.Z

        n.ReferenceType = "OCCURRENCE_CENTER"

    Next

End Sub



' ===================================================================
' BUILD MANUFACTURING PRIMITIVES
' ===================================================================

Function BuildManufacturingPrimitives( _
    nodes As List(Of NodeRecord), _
    edges As List(Of EdgeRecord)) As List(Of PrimitiveSegment)


    Dim result As New List(Of PrimitiveSegment)


    For Each n As NodeRecord In nodes


        Dim activePorts As List(Of PortRecord) = _
            GetUsedPorts(n, edges)


        Select Case n.ComponentType


            Case "FLANGE"

                If n.HasOuterAnchor Then


                    Dim hostPort As PortRecord = _
                        GetHostSidePortForFlange( _
                            n, _
                            edges)


                    If hostPort IsNot Nothing Then


                        result.Add( _
                            New PrimitiveSegment( _
                                n, _
                                "FLANGE", _
                                hostPort.X, _
                                hostPort.Y, _
                                hostPort.Z, _
                                n.OuterX, _
                                n.OuterY, _
                                n.OuterZ))

                    End If

                End If


            Case "PIPE", _
                 "REDUCER", _
                 "VALVE", _
                 "COUPLING_SOCKET", _
                 "OTHER"


                If activePorts.Count >= 2 Then


                    Dim a As PortRecord = Nothing
                    Dim b As PortRecord = Nothing


                    FindFarthestPortPair( _
                        activePorts, _
                        a, _
                        b)


                    If a IsNot Nothing AndAlso _
                       b IsNot Nothing Then


                        result.Add( _
                            New PrimitiveSegment( _
                                n, _
                                n.ComponentType, _
                                a.X, a.Y, a.Z, _
                                b.X, b.Y, b.Z))

                    End If

                End If


            Case "TEE"


                For Each p As PortRecord In activePorts


                    result.Add( _
                        New PrimitiveSegment( _
                            n, _
                            "TEE_LEG", _
                            n.RefX, _
                            n.RefY, _
                            n.RefZ, _
                            p.X, _
                            p.Y, _
                            p.Z))

                Next


            Case "ELBOW"


                For Each p As PortRecord In activePorts


                    result.Add( _
                        New PrimitiveSegment( _
                            n, _
                            "ELBOW_RADIAL", _
                            n.RefX, _
                            n.RefY, _
                            n.RefZ, _
                            p.X, _
                            p.Y, _
                            p.Z))

                Next

        End Select

    Next


    Return result

End Function



' ===================================================================
' COMPONENT DIMENSIONS
' ===================================================================

Function BuildComponentDimensions( _
    nodes As List(Of NodeRecord), _
    edges As List(Of EdgeRecord)) As List(Of DimensionRecord)


    Dim result As New List(Of DimensionRecord)


    For Each n As NodeRecord In nodes


        Dim activePorts As List(Of PortRecord) = _
            GetUsedPorts(n, edges)


        Select Case n.ComponentType


            Case "FLANGE"

                If n.HasOuterAnchor Then


                    Dim hostPort As PortRecord = _
                        GetHostSidePortForFlange( _
                            n, _
                            edges)


                    If hostPort IsNot Nothing Then


                        AddDimension( _
                            result, _
                            n.Code & " FLANGE", _
                            n.Code, _
                            "FLANGE_THICKNESS", _
                            hostPort.X, _
                            hostPort.Y, _
                            hostPort.Z, _
                            n.OuterX, _
                            n.OuterY, _
                            n.OuterZ, _
                            "COMPONENT")

                    End If

                End If


            Case "PIPE"


                If activePorts.Count >= 2 Then


                    Dim a As PortRecord = Nothing
                    Dim b As PortRecord = Nothing


                    FindFarthestPortPair( _
                        activePorts, _
                        a, _
                        b)


                    If a IsNot Nothing AndAlso _
                       b IsNot Nothing Then


                        AddDimension( _
                            result, _
                            n.Code & " PIPE", _
                            n.Code, _
                            "PIPE_LENGTH", _
                            a.X, a.Y, a.Z, _
                            b.X, b.Y, b.Z, _
                            "COMPONENT")

                    End If

                End If


            Case "REDUCER"


                If activePorts.Count >= 2 Then


                    Dim a As PortRecord = Nothing
                    Dim b As PortRecord = Nothing


                    FindFarthestPortPair( _
                        activePorts, _
                        a, _
                        b)


                    If a IsNot Nothing AndAlso _
                       b IsNot Nothing Then


                        AddDimension( _
                            result, _
                            n.Code & " REDUCER", _
                            n.Code, _
                            "REDUCER_FACE_TO_FACE", _
                            a.X, a.Y, a.Z, _
                            b.X, b.Y, b.Z, _
                            "COMPONENT")

                    End If

                End If


            Case "TEE"


                If activePorts.Count >= 2 Then


                    Dim runA As PortRecord = Nothing
                    Dim runB As PortRecord = Nothing


                    FindMostOpposedPortPair( _
                        activePorts, _
                        runA, _
                        runB)


                    If runA IsNot Nothing AndAlso _
                       runB IsNot Nothing Then


                        AddDimension( _
                            result, _
                            n.Code & " TEE RUN", _
                            n.Code, _
                            "TEE_RUN_FACE_TO_FACE", _
                            runA.X, runA.Y, runA.Z, _
                            runB.X, runB.Y, runB.Z, _
                            "COMPONENT")

                    End If


                    For Each p As PortRecord In activePorts


                        If p Is runA OrElse p Is runB Then
                            Continue For
                        End If


                        AddDimension( _
                            result, _
                            n.Code & " TEE BRANCH", _
                            n.Code, _
                            "TEE_CENTER_TO_BRANCH_FACE", _
                            n.RefX, n.RefY, n.RefZ, _
                            p.X, p.Y, p.Z, _
                            "COMPONENT")

                    Next

                End If


            Case "ELBOW"


                For i As Integer = 0 To activePorts.Count - 1


                    Dim p As PortRecord = _
                        activePorts.Item(i)


                    AddDimension( _
                        result, _
                        n.Code & " ELBOW R" & _
                        (i + 1).ToString(), _
                        n.Code, _
                        "ELBOW_CENTER_TO_PORT", _
                        n.RefX, n.RefY, n.RefZ, _
                        p.X, p.Y, p.Z, _
                        "COMPONENT")

                Next


            Case "VALVE", _
                 "COUPLING_SOCKET"


                If activePorts.Count >= 2 Then


                    Dim a As PortRecord = Nothing
                    Dim b As PortRecord = Nothing


                    FindFarthestPortPair( _
                        activePorts, _
                        a, _
                        b)


                    If a IsNot Nothing AndAlso _
                       b IsNot Nothing Then


                        AddDimension( _
                            result, _
                            n.Code & " " & n.ComponentType, _
                            n.Code, _
                            n.ComponentType & "_FACE_TO_FACE", _
                            a.X, a.Y, a.Z, _
                            b.X, b.Y, b.Z, _
                            "COMPONENT")

                    End If

                End If

        End Select

    Next


    Return result

End Function



Sub AddDimension( _
    list As List(Of DimensionRecord), _
    label As String, _
    ownerCode As String, _
    dimensionType As String, _
    ax As Double, _
    ay As Double, _
    az As Double, _
    bx As Double, _
    by As Double, _
    bz As Double, _
    category As String)


    Dim d As New DimensionRecord

    d.Label = label
    d.OwnerCode = ownerCode
    d.DimensionType = dimensionType
    d.Category = category

    d.X1 = ax
    d.Y1 = ay
    d.Z1 = az

    d.X2 = bx
    d.Y2 = by
    d.Z2 = bz

    d.Value = _
        Dist3D( _
            ax, ay, az, _
            bx, by, bz)


    list.Add(d)

End Sub



' ===================================================================
' BUILD MAXIMAL STRAIGHT CHAINS
' ===================================================================

Function BuildStraightChains( _
    segments As List(Of PrimitiveSegment)) As List(Of StraightChain)


    Dim result As New List(Of StraightChain)

    Dim visited As New HashSet(Of Integer)


    For i As Integer = 0 To segments.Count - 1


        If visited.Contains(i) Then
            Continue For
        End If


        Dim queue As New Queue(Of Integer)
        Dim indices As New List(Of Integer)


        queue.Enqueue(i)
        visited.Add(i)


        While queue.Count > 0


            Dim current As Integer = queue.Dequeue()

            indices.Add(current)


            For j As Integer = 0 To segments.Count - 1


                If visited.Contains(j) Then
                    Continue For
                End If


                If SegmentsConnectCollinear( _
                    segments.Item(current), _
                    segments.Item(j)) Then


                    visited.Add(j)
                    queue.Enqueue(j)

                End If

            Next

        End While


        Dim chain As New StraightChain

        chain.Index = result.Count + 1


        For Each idx As Integer In indices

            chain.Segments.Add( _
                segments.Item(idx))

        Next


        ComputeChainExtremes(chain)


        result.Add(chain)

    Next


    Return result

End Function



Function SegmentsConnectCollinear( _
    a As PrimitiveSegment, _
    b As PrimitiveSegment) As Boolean


    If Not SegmentsShareEndpoint(a, b, 0.5) Then
        Return False
    End If


    Dim adx As Double = a.X2 - a.X1
    Dim ady As Double = a.Y2 - a.Y1
    Dim adz As Double = a.Z2 - a.Z1

    Dim bdx As Double = b.X2 - b.X1
    Dim bdy As Double = b.Y2 - b.Y1
    Dim bdz As Double = b.Z2 - b.Z1


    Dim al As Double = _
        Math.Sqrt( _
            adx * adx + _
            ady * ady + _
            adz * adz)

    Dim bl As Double = _
        Math.Sqrt( _
            bdx * bdx + _
            bdy * bdy + _
            bdz * bdz)


    If al < 0.001 OrElse bl < 0.001 Then
        Return False
    End If


    Dim dotValue As Double = _
        Math.Abs( _
            (adx * bdx + _
             ady * bdy + _
             adz * bdz) / _
            (al * bl))


    Return dotValue >= 0.999

End Function



Function SegmentsShareEndpoint( _
    a As PrimitiveSegment, _
    b As PrimitiveSegment, _
    tolerance As Double) As Boolean


    If Dist3D( _
        a.X1, a.Y1, a.Z1, _
        b.X1, b.Y1, b.Z1) <= tolerance Then

        Return True
    End If


    If Dist3D( _
        a.X1, a.Y1, a.Z1, _
        b.X2, b.Y2, b.Z2) <= tolerance Then

        Return True
    End If


    If Dist3D( _
        a.X2, a.Y2, a.Z2, _
        b.X1, b.Y1, b.Z1) <= tolerance Then

        Return True
    End If


    If Dist3D( _
        a.X2, a.Y2, a.Z2, _
        b.X2, b.Y2, b.Z2) <= tolerance Then

        Return True
    End If


    Return False

End Function



Sub ComputeChainExtremes( _
    chain As StraightChain)


    Dim points As New List(Of Point3DRecord)


    For Each s As PrimitiveSegment In chain.Segments

        points.Add( _
            New Point3DRecord( _
                s.X1, s.Y1, s.Z1))

        points.Add( _
            New Point3DRecord( _
                s.X2, s.Y2, s.Z2))

    Next


    Dim best As Double = -1


    For i As Integer = 0 To points.Count - 2

        For j As Integer = i + 1 To points.Count - 1


            Dim a As Point3DRecord = points.Item(i)
            Dim b As Point3DRecord = points.Item(j)


            Dim d As Double = _
                Dist3D( _
                    a.X, a.Y, a.Z, _
                    b.X, b.Y, b.Z)


            If d > best Then

                best = d

                chain.X1 = a.X
                chain.Y1 = a.Y
                chain.Z1 = a.Z

                chain.X2 = b.X
                chain.Y2 = b.Y
                chain.Z2 = b.Z

            End If

        Next

    Next


    chain.Length = Math.Max(best, 0)

End Sub



Function BuildOverallDimensions( _
    chains As List(Of StraightChain)) As List(Of DimensionRecord)


    Dim result As New List(Of DimensionRecord)


    For Each chain As StraightChain In chains


        ' -----------------------------------------------------------
        ' Only useful as an OVERALL when the straight chain consists
        ' of more than one manufacturing primitive.
        ' -----------------------------------------------------------

        If chain.Segments.Count <= 1 Then
            Continue For
        End If


        Dim d As New DimensionRecord

        d.Label = _
            "RUN " & _
            chain.Index.ToString() & _
            " OVERALL"

        d.OwnerCode = "RUN" & chain.Index.ToString()
        d.DimensionType = "STRAIGHT_RUN_OVERALL"
        d.Category = "OVERALL"

        d.ChainIndex = chain.Index

        d.X1 = chain.X1
        d.Y1 = chain.Y1
        d.Z1 = chain.Z1

        d.X2 = chain.X2
        d.Y2 = chain.Y2
        d.Z2 = chain.Z2

        d.Value = chain.Length


        result.Add(d)

    Next


    Return result

End Function



Sub AssignDimensionsToChains( _
    dimensions As List(Of DimensionRecord), _
    chains As List(Of StraightChain))


    For Each d As DimensionRecord In dimensions


        d.ChainIndex = 0


        For Each chain As StraightChain In chains


            If PointOnInfiniteLine( _
                d.X1, d.Y1, d.Z1, _
                chain.X1, chain.Y1, chain.Z1, _
                chain.X2, chain.Y2, chain.Z2, _
                0.75) AndAlso _
               PointOnInfiniteLine( _
                d.X2, d.Y2, d.Z2, _
                chain.X1, chain.Y1, chain.Z1, _
                chain.X2, chain.Y2, chain.Z2, _
                0.75) Then


                d.ChainIndex = chain.Index
                Exit For

            End If

        Next

    Next

End Sub



Function PointOnInfiniteLine( _
    px As Double, _
    py As Double, _
    pz As Double, _
    ax As Double, _
    ay As Double, _
    az As Double, _
    bx As Double, _
    by As Double, _
    bz As Double, _
    tolerance As Double) As Boolean


    Dim dx As Double = bx - ax
    Dim dy As Double = by - ay
    Dim dz As Double = bz - az


    Dim length As Double = _
        Math.Sqrt( _
            dx * dx + _
            dy * dy + _
            dz * dz)


    If length < 0.001 Then
        Return False
    End If


    dx /= length
    dy /= length
    dz /= length


    Dim vx As Double = px - ax
    Dim vy As Double = py - ay
    Dim vz As Double = pz - az


    Dim projection As Double = _
        vx * dx + _
        vy * dy + _
        vz * dz


    Dim cx As Double = ax + projection * dx
    Dim cy As Double = ay + projection * dy
    Dim cz As Double = az + projection * dz


    Dim perpendicular As Double = _
        Dist3D( _
            px, py, pz, _
            cx, cy, cz)


    Return perpendicular <= tolerance

End Function



' ===================================================================
' COMPLETE CSV
' ===================================================================

Sub WriteCompleteCsv( _
    assemblyName As String, _
    nodes As List(Of NodeRecord), _
    edges As List(Of EdgeRecord), _
    primitives As List(Of PrimitiveSegment), _
    componentDimensions As List(Of DimensionRecord), _
    chains As List(Of StraightChain), _
    overallDimensions As List(Of DimensionRecord), _
    graphGroups As Integer, _
    unresolved As List(Of String), _
    outputFile As String)


    Dim writer As New System.IO.StreamWriter( _
        outputFile, _
        False, _
        Encoding.UTF8)


    Try

        writer.WriteLine( _
            "RecordType," & _
            "Assembly," & _
            "Code," & _
            "OwnerCode," & _
            "Occurrence," & _
            "ComponentType," & _
            "PartNumber," & _
            "Description," & _
            "FaceIndex," & _
            "X_mm," & _
            "Y_mm," & _
            "Z_mm," & _
            "NX," & _
            "NY," & _
            "NZ," & _
            "Radius_mm," & _
            "Used," & _
            "ConnectedTo," & _
            "ConnectionType," & _
            "ConnectionDistance_mm," & _
            "ReferenceType," & _
            "ReferenceX_mm," & _
            "ReferenceY_mm," & _
            "ReferenceZ_mm," & _
            "FlangeInnerFace," & _
            "FlangeOuterFace," & _
            "FlangeOuterX_mm," & _
            "FlangeOuterY_mm," & _
            "FlangeOuterZ_mm," & _
            "Value_mm," & _
            "FromX_mm," & _
            "FromY_mm," & _
            "FromZ_mm," & _
            "ToX_mm," & _
            "ToY_mm," & _
            "ToZ_mm," & _
            "ChainIndex," & _
            "Notes")


        ' -----------------------------------------------------------
        ' Assembly summary
        ' -----------------------------------------------------------

        writer.WriteLine( _
            Csv("ASSEMBLY") & "," & _
            Csv(assemblyName) & "," & _
            Csv("") & "," & _
            Csv("") & "," & _
            Csv("") & "," & _
            Csv("") & "," & _
            Csv("") & "," & _
            Csv("") & "," & _
            "," & _
            "," & "," & "," & _
            "," & "," & "," & _
            "," & _
            Csv("") & "," & _
            Csv("") & "," & _
            Csv("") & "," & _
            "," & _
            Csv("") & "," & _
            "," & "," & "," & _
            "," & "," & _
            "," & "," & "," & _
            "," & _
            "," & "," & "," & _
            "," & "," & "," & _
            "," & _
            Csv( _
                "Components=" & nodes.Count.ToString() & _
                "; Connections=" & edges.Count.ToString() & _
                "; GraphGroups=" & graphGroups.ToString() & _
                "; Unresolved=" & _
                String.Join(";", unresolved.ToArray())))


        ' -----------------------------------------------------------
        ' Components + ports
        ' -----------------------------------------------------------

        For Each n As NodeRecord In nodes


            writer.WriteLine( _
                Csv("COMPONENT") & "," & _
                Csv(assemblyName) & "," & _
                Csv(n.Code) & "," & _
                Csv(n.Code) & "," & _
                Csv(n.OccurrenceName) & "," & _
                Csv(n.ComponentType) & "," & _
                Csv(n.PartNumber) & "," & _
                Csv(n.Description) & "," & _
                "," & _
                Num(n.X) & "," & _
                Num(n.Y) & "," & _
                Num(n.Z) & "," & _
                "," & "," & "," & _
                "," & _
                Csv("") & "," & _
                Csv(String.Join(";", GetNeighbourCodes(n).ToArray())) & "," & _
                Csv("") & "," & _
                "," & _
                Csv(n.ReferenceType) & "," & _
                Num(n.RefX) & "," & _
                Num(n.RefY) & "," & _
                Num(n.RefZ) & "," & _
                If(n.InnerFaceIndex > 0, n.InnerFaceIndex.ToString(), "") & "," & _
                If(n.OuterFaceIndex > 0, n.OuterFaceIndex.ToString(), "") & "," & _
                If(n.HasOuterAnchor, Num(n.OuterX), "") & "," & _
                If(n.HasOuterAnchor, Num(n.OuterY), "") & "," & _
                If(n.HasOuterAnchor, Num(n.OuterZ), "") & "," & _
                If(n.HasOuterAnchor, Num(n.OuterOffset), "") & "," & _
                "," & "," & "," & _
                "," & "," & "," & _
                "," & _
                Csv( _
                    "Degree=" & _
                    n.Neighbours.Count.ToString()))


            For Each p As PortRecord In n.Ports


                writer.WriteLine( _
                    Csv("PORT") & "," & _
                    Csv(assemblyName) & "," & _
                    Csv(n.Code) & "," & _
                    Csv(n.Code) & "," & _
                    Csv(n.OccurrenceName) & "," & _
                    Csv(n.ComponentType) & "," & _
                    Csv(n.PartNumber) & "," & _
                    Csv(n.Description) & "," & _
                    p.FaceIndex.ToString() & "," & _
                    Num(p.X) & "," & _
                    Num(p.Y) & "," & _
                    Num(p.Z) & "," & _
                    Num(p.NX) & "," & _
                    Num(p.NY) & "," & _
                    Num(p.NZ) & "," & _
                    Num(p.Radius) & "," & _
                    Csv(If(p.Used, "YES", "NO")) & "," & _
                    Csv("") & "," & _
                    Csv("") & "," & _
                    "," & _
                    Csv("") & "," & _
                    "," & "," & "," & _
                    "," & "," & "," & "," & "," & _
                    "," & _
                    "," & "," & "," & _
                    "," & "," & "," & _
                    "," & _
                    Csv( _
                        "CircularEdges=" & _
                        p.CircularEdges.ToString() & _
                        "; FaceArea_mm2=" & _
                        Num(p.FaceArea)))

            Next

        Next


        ' -----------------------------------------------------------
        ' Connections
        ' -----------------------------------------------------------

        For Each e As EdgeRecord In edges


            writer.WriteLine( _
                Csv("CONNECTION") & "," & _
                Csv(assemblyName) & "," & _
                Csv(e.A.Code & "-" & e.B.Code) & "," & _
                Csv("") & "," & _
                Csv("") & "," & _
                Csv("") & "," & _
                Csv("") & "," & _
                Csv("") & "," & _
                "," & _
                Num(e.PortA.X) & "," & _
                Num(e.PortA.Y) & "," & _
                Num(e.PortA.Z) & "," & _
                Num(e.PortA.NX) & "," & _
                Num(e.PortA.NY) & "," & _
                Num(e.PortA.NZ) & "," & _
                "," & _
                Csv("") & "," & _
                Csv(e.B.Code) & "," & _
                Csv(e.ConnectionType) & "," & _
                Num(e.ConnectionDistance) & "," & _
                Csv("") & "," & _
                "," & "," & "," & _
                "," & "," & "," & "," & "," & _
                "," & _
                "," & "," & "," & _
                "," & "," & "," & _
                "," & _
                Csv( _
                    "PortA_Face=" & e.PortA.FaceIndex.ToString() & _
                    "; PortB_Face=" & e.PortB.FaceIndex.ToString()))

        Next


        ' -----------------------------------------------------------
        ' Primitive skeleton
        ' -----------------------------------------------------------

        For Each p As PrimitiveSegment In primitives


            writer.WriteLine( _
                Csv("PRIMITIVE") & "," & _
                Csv(assemblyName) & "," & _
                Csv(p.Owner.Code & "-" & p.Kind) & "," & _
                Csv(p.Owner.Code) & "," & _
                Csv(p.Owner.OccurrenceName) & "," & _
                Csv(p.Owner.ComponentType) & "," & _
                Csv(p.Owner.PartNumber) & "," & _
                Csv(p.Owner.Description) & "," & _
                "," & _
                "," & "," & "," & _
                "," & "," & "," & _
                "," & _
                Csv("") & "," & _
                Csv("") & "," & _
                Csv(p.Kind) & "," & _
                "," & _
                Csv("") & "," & _
                "," & "," & "," & _
                "," & "," & "," & "," & "," & _
                Num(p.Length) & "," & _
                Num(p.X1) & "," & _
                Num(p.Y1) & "," & _
                Num(p.Z1) & "," & _
                Num(p.X2) & "," & _
                Num(p.Y2) & "," & _
                Num(p.Z2) & "," & _
                "," & _
                Csv("Manufacturing skeleton segment"))

        Next


        ' -----------------------------------------------------------
        ' Component dimensions
        ' -----------------------------------------------------------

        For Each d As DimensionRecord In componentDimensions


            WriteDimensionCsvRow( _
                writer, _
                assemblyName, _
                "COMPONENT_DIMENSION", _
                d)

        Next


        ' -----------------------------------------------------------
        ' Overall dimensions
        ' -----------------------------------------------------------

        For Each d As DimensionRecord In overallDimensions


            WriteDimensionCsvRow( _
                writer, _
                assemblyName, _
                "OVERALL_DIMENSION", _
                d)

        Next


        writer.Flush()


    Finally

        writer.Close()

    End Try

End Sub



Sub WriteDimensionCsvRow( _
    writer As System.IO.StreamWriter, _
    assemblyName As String, _
    recordType As String, _
    d As DimensionRecord)


    writer.WriteLine( _
        Csv(recordType) & "," & _
        Csv(assemblyName) & "," & _
        Csv(d.Label) & "," & _
        Csv(d.OwnerCode) & "," & _
        Csv("") & "," & _
        Csv("") & "," & _
        Csv("") & "," & _
        Csv("") & "," & _
        "," & _
        "," & "," & "," & _
        "," & "," & "," & _
        "," & _
        Csv("") & "," & _
        Csv("") & "," & _
        Csv(d.DimensionType) & "," & _
        "," & _
        Csv(d.Category) & "," & _
        "," & "," & "," & _
        "," & "," & "," & "," & "," & _
        Num(d.Value) & "," & _
        Num(d.X1) & "," & _
        Num(d.Y1) & "," & _
        Num(d.Z1) & "," & _
        Num(d.X2) & "," & _
        Num(d.Y2) & "," & _
        Num(d.Z2) & "," & _
        d.ChainIndex.ToString() & "," & _
        Csv(""))

End Sub



' ===================================================================
' CLEAN CANONICAL SCHEMATIC
' ===================================================================

Sub GenerateVerificationSvg( _
    assemblyName As String, _
    nodes As List(Of NodeRecord), _
    edges As List(Of EdgeRecord), _
    primitives As List(Of PrimitiveSegment), _
    componentDimensions As List(Of DimensionRecord), _
    chains As List(Of StraightChain), _
    overallDimensions As List(Of DimensionRecord), _
    graphGroups As Integer, _
    unresolved As List(Of String), _
    outputFile As String)


    Dim canvasWidth As Double = 1600
    Dim canvasHeight As Double = 1050


    Dim svg As New StringBuilder


    svg.AppendLine( _
        "<svg xmlns=""http://www.w3.org/2000/svg"" " & _
        "width=""" & Num(canvasWidth) & """ " & _
        "height=""" & Num(canvasHeight) & """ " & _
        "viewBox=""0 0 1600 1050"">")


    svg.AppendLine( _
        "<rect x=""1"" y=""1"" width=""1598"" height=""1048"" " & _
        "fill=""white"" stroke=""black"" stroke-width=""2""/>")


    svg.AppendLine( _
        "<text x=""40"" y=""44"" " & _
        "font-family=""Arial"" font-size=""25"" font-weight=""bold"">" & _
        XmlText(assemblyName) & _
        "</text>")


    svg.AppendLine( _
        "<text x=""40"" y=""72"" " & _
        "font-family=""Arial"" font-size=""14"">" & _
        XmlText( _
            "Components=" & nodes.Count.ToString() & _
            "   Connections=" & edges.Count.ToString() & _
            "   GraphGroups=" & graphGroups.ToString() & _
            "   Unresolved=" & _
            String.Join(",", unresolved.ToArray())) & _
        "</text>")


    svg.AppendLine( _
        "<text x=""40"" y=""96"" " & _
        "font-family=""Arial"" font-size=""12"">" & _
        "Component dimensions + maximal straight-run overall dimensions extracted from model geometry." & _
        "</text>")


    ' ===============================================================
    ' Main schematic panel
    ' ===============================================================

    Dim panelX As Double = 30
    Dim panelY As Double = 120
    Dim panelW As Double = 1540
    Dim panelH As Double = 760


    svg.AppendLine( _
        "<rect x=""" & Num(panelX) & _
        """ y=""" & Num(panelY) & _
        """ width=""" & Num(panelW) & _
        """ height=""" & Num(panelH) & _
        """ fill=""none"" stroke=""black"" stroke-width=""1.5""/>")


    svg.AppendLine( _
        "<text x=""" & Num(panelX + 14) & _
        """ y=""" & Num(panelY + 27) & _
        """ font-family=""Arial"" font-size=""16"" font-weight=""bold"">" & _
        "CANONICAL MANUFACTURING SCHEMATIC" & _
        "</text>")


    Dim transform As SchematicTransform = _
        BuildCanonicalTransform( _
            nodes, _
            primitives, _
            chains, _
            panelX + 90, _
            panelY + 95, _
            panelW - 180, _
            panelH - 190)


    ' ===============================================================
    ' Draw manufacturing geometry
    ' ===============================================================

    DrawManufacturingGeometry( _
        svg, _
        nodes, _
        edges, _
        primitives, _
        transform)


    ' ===============================================================
    ' Component labels
    ' ===============================================================

    DrawComponentLabels( _
        svg, _
        nodes, _
        transform)


    ' ===============================================================
    ' Dimensions
    ' ===============================================================

    DrawAllDimensions( _
        svg, _
        componentDimensions, _
        chains, _
        overallDimensions, _
        transform)


    ' ===============================================================
    ' Bottom extracted dimension table
    ' ===============================================================

    DrawDimensionSummaryTable( _
        svg, _
        componentDimensions, _
        overallDimensions, _
        50, _
        910)


    svg.AppendLine("</svg>")


    System.IO.File.WriteAllText( _
        outputFile, _
        svg.ToString(), _
        Encoding.UTF8)

End Sub



' ===================================================================
' BUILD CANONICAL 2D BASIS
'
' Primary U axis = longest straight chain.
'
' Secondary V axis:
' prefer a non-collinear TEE branch so branch direction is visually
' meaningful.  Otherwise use any non-collinear primitive.
'
' This makes a planar spool like:
'
'             branch
'               |
' flange--pipe--tee----elbow
'                         |
'                       flange
'
' appear in the natural fabrication orientation.
' ===================================================================

Function BuildCanonicalTransform( _
    nodes As List(Of NodeRecord), _
    primitives As List(Of PrimitiveSegment), _
    chains As List(Of StraightChain), _
    x As Double, _
    y As Double, _
    w As Double, _
    h As Double) As SchematicTransform


    Dim t As New SchematicTransform


    ' ---------------------------------------------------------------
    ' Find longest straight chain.
    ' ---------------------------------------------------------------

    Dim longest As StraightChain = Nothing


    For Each c As StraightChain In chains

        If longest Is Nothing OrElse _
           c.Length > longest.Length Then

            longest = c

        End If

    Next


    Dim ux As Double = 1
    Dim uy As Double = 0
    Dim uz As Double = 0


    Dim originX As Double = 0
    Dim originY As Double = 0
    Dim originZ As Double = 0


    If longest IsNot Nothing AndAlso _
       longest.Length > 0.001 Then


        ' -----------------------------------------------------------
        ' Prefer a flange outer endpoint as LEFT/start of main chain.
        ' -----------------------------------------------------------

        Dim aIsFlange As Boolean = _
            IsFlangeOuterPoint( _
                nodes, _
                longest.X1, _
                longest.Y1, _
                longest.Z1)

        Dim bIsFlange As Boolean = _
            IsFlangeOuterPoint( _
                nodes, _
                longest.X2, _
                longest.Y2, _
                longest.Z2)


        If bIsFlange AndAlso Not aIsFlange Then

            originX = longest.X2
            originY = longest.Y2
            originZ = longest.Z2

            ux = longest.X1 - longest.X2
            uy = longest.Y1 - longest.Y2
            uz = longest.Z1 - longest.Z2

        Else

            originX = longest.X1
            originY = longest.Y1
            originZ = longest.Z1

            ux = longest.X2 - longest.X1
            uy = longest.Y2 - longest.Y1
            uz = longest.Z2 - longest.Z1

        End If

    ElseIf primitives.Count > 0 Then


        Dim s As PrimitiveSegment = _
            primitives.Item(0)


        originX = s.X1
        originY = s.Y1
        originZ = s.Z1

        ux = s.X2 - s.X1
        uy = s.Y2 - s.Y1
        uz = s.Z2 - s.Z1

    End If


    NormalizeVector(ux, uy, uz)


    ' ---------------------------------------------------------------
    ' Find a meaningful secondary direction.
    ' Prefer TEE branch not collinear with U.
    ' ---------------------------------------------------------------

    Dim sx As Double = 0
    Dim sy As Double = 0
    Dim sz As Double = 0

    Dim foundSecondary As Boolean = False


    For Each s As PrimitiveSegment In primitives


        If s.Owner.ComponentType <> "TEE" Then
            Continue For
        End If


        Dim dx As Double = s.X2 - s.X1
        Dim dy As Double = s.Y2 - s.Y1
        Dim dz As Double = s.Z2 - s.Z1


        Dim dl As Double = _
            Math.Sqrt( _
                dx * dx + _
                dy * dy + _
                dz * dz)


        If dl < 0.001 Then
            Continue For
        End If


        dx /= dl
        dy /= dl
        dz /= dl


        Dim dotValue As Double = _
            Math.Abs( _
                dx * ux + _
                dy * uy + _
                dz * uz)


        If dotValue < 0.90 Then

            sx = dx
            sy = dy
            sz = dz

            foundSecondary = True
            Exit For

        End If

    Next


    If Not foundSecondary Then


        For Each s As PrimitiveSegment In primitives


            Dim dx As Double = s.X2 - s.X1
            Dim dy As Double = s.Y2 - s.Y1
            Dim dz As Double = s.Z2 - s.Z1


            Dim dl As Double = _
                Math.Sqrt( _
                    dx * dx + _
                    dy * dy + _
                    dz * dz)


            If dl < 0.001 Then
                Continue For
            End If


            dx /= dl
            dy /= dl
            dz /= dl


            Dim dotValue As Double = _
                Math.Abs( _
                    dx * ux + _
                    dy * uy + _
                    dz * uz)


            If dotValue < 0.90 Then

                sx = dx
                sy = dy
                sz = dz

                foundSecondary = True
                Exit For

            End If

        Next

    End If


    ' ---------------------------------------------------------------
    ' If entire spool is straight, manufacture an arbitrary
    ' perpendicular V.
    ' ---------------------------------------------------------------

    If Not foundSecondary Then


        If Math.Abs(ux) < 0.8 Then

            sx = 1
            sy = 0
            sz = 0

        Else

            sx = 0
            sy = 1
            sz = 0

        End If

    End If


    ' ---------------------------------------------------------------
    ' Plane normal N = secondary x U.
    ' Then V = U x N.
    '
    ' This makes V point approximately in secondary direction.
    ' ---------------------------------------------------------------

    Dim nx As Double = _
        sy * uz - _
        sz * uy

    Dim ny As Double = _
        sz * ux - _
        sx * uz

    Dim nz As Double = _
        sx * uy - _
        sy * ux


    NormalizeVector(nx, ny, nz)


    Dim vx As Double = _
        uy * nz - _
        uz * ny

    Dim vy As Double = _
        uz * nx - _
        ux * nz

    Dim vz As Double = _
        ux * ny - _
        uy * nx


    NormalizeVector(vx, vy, vz)


    t.OriginX = originX
    t.OriginY = originY
    t.OriginZ = originZ

    t.UX = ux
    t.UY = uy
    t.UZ = uz

    t.VX = vx
    t.VY = vy
    t.VZ = vz


    ' ---------------------------------------------------------------
    ' Fit all primitive endpoints + references in panel.
    ' ---------------------------------------------------------------

    Dim samplePoints As New List(Of Point3DRecord)


    For Each s As PrimitiveSegment In primitives

        samplePoints.Add( _
            New Point3DRecord( _
                s.X1, s.Y1, s.Z1))

        samplePoints.Add( _
            New Point3DRecord( _
                s.X2, s.Y2, s.Z2))

    Next


    For Each n As NodeRecord In nodes

        samplePoints.Add( _
            New Point3DRecord( _
                n.RefX, _
                n.RefY, _
                n.RefZ))

    Next


    Dim minU As Double = Double.MaxValue
    Dim maxU As Double = Double.MinValue

    Dim minV As Double = Double.MaxValue
    Dim maxV As Double = Double.MinValue


    For Each p As Point3DRecord In samplePoints


        Dim pu As Double = 0
        Dim pv As Double = 0


        ProjectToCanonical( _
            t, _
            p.X, p.Y, p.Z, _
            pu, pv)


        If pu < minU Then minU = pu
        If pu > maxU Then maxU = pu

        If pv < minV Then minV = pv
        If pv > maxV Then maxV = pv

    Next


    If samplePoints.Count = 0 Then

        minU = 0
        maxU = 1
        minV = 0
        maxV = 1

    End If


    Dim rangeU As Double = maxU - minU
    Dim rangeV As Double = maxV - minV


    If rangeU < 1 Then rangeU = 1
    If rangeV < 1 Then rangeV = 1


    ' Leave plenty of space for dimensions.
    Dim geometryW As Double = w * 0.72
    Dim geometryH As Double = h * 0.58


    Dim scaleU As Double = geometryW / rangeU
    Dim scaleV As Double = geometryH / rangeV


    t.Scale = Math.Min(scaleU, scaleV)


    Dim usedW As Double = rangeU * t.Scale
    Dim usedH As Double = rangeV * t.Scale


    t.ScreenOriginX = _
        x + _
        (w - usedW) / 2.0 - _
        minU * t.Scale

    t.ScreenOriginY = _
        y + _
        (h - usedH) / 2.0 + _
        maxV * t.Scale


    Return t

End Function



Function IsFlangeOuterPoint( _
    nodes As List(Of NodeRecord), _
    x As Double, _
    y As Double, _
    z As Double) As Boolean


    For Each n As NodeRecord In nodes


        If n.ComponentType <> "FLANGE" OrElse _
           Not n.HasOuterAnchor Then

            Continue For
        End If


        If Dist3D( _
            x, y, z, _
            n.OuterX, n.OuterY, n.OuterZ) <= 0.5 Then

            Return True

        End If

    Next


    Return False

End Function



Sub ProjectToCanonical( _
    t As SchematicTransform, _
    x As Double, _
    y As Double, _
    z As Double, _
    ByRef u As Double, _
    ByRef v As Double)


    Dim dx As Double = x - t.OriginX
    Dim dy As Double = y - t.OriginY
    Dim dz As Double = z - t.OriginZ


    u = _
        dx * t.UX + _
        dy * t.UY + _
        dz * t.UZ

    v = _
        dx * t.VX + _
        dy * t.VY + _
        dz * t.VZ

End Sub



Function MapCanonicalPoint( _
    t As SchematicTransform, _
    x As Double, _
    y As Double, _
    z As Double) As SvgPoint


    Dim u As Double = 0
    Dim v As Double = 0


    ProjectToCanonical( _
        t, _
        x, y, z, _
        u, v)


    Return _
        New SvgPoint( _
            t.ScreenOriginX + _
            u * t.Scale, _
            t.ScreenOriginY - _
            v * t.Scale)

End Function



' ===================================================================
' DRAW MANUFACTURING GEOMETRY
' ===================================================================

Sub DrawManufacturingGeometry( _
    svg As StringBuilder, _
    nodes As List(Of NodeRecord), _
    edges As List(Of EdgeRecord), _
    primitives As List(Of PrimitiveSegment), _
    transform As SchematicTransform)


    ' ---------------------------------------------------------------
    ' Generic straight primitives except flange and elbow radial.
    ' ---------------------------------------------------------------

    For Each p As PrimitiveSegment In primitives


        If p.Kind = "FLANGE" Then
            Continue For
        End If


        If p.Kind = "ELBOW_RADIAL" Then
            Continue For
        End If


        Dim a As SvgPoint = _
            MapCanonicalPoint( _
                transform, _
                p.X1, p.Y1, p.Z1)

        Dim b As SvgPoint = _
            MapCanonicalPoint( _
                transform, _
                p.X2, p.Y2, p.Z2)


        svg.AppendLine( _
            "<line x1=""" & Num(a.X) & _
            """ y1=""" & Num(a.Y) & _
            """ x2=""" & Num(b.X) & _
            """ y2=""" & Num(b.Y) & _
            """ stroke=""black"" stroke-width=""4""/>")

    Next


    ' ---------------------------------------------------------------
    ' Flanges = two short perpendicular face lines separated by the
    ' extracted flange thickness.
    ' ---------------------------------------------------------------

    For Each n As NodeRecord In nodes


        If n.ComponentType <> "FLANGE" OrElse _
           Not n.HasOuterAnchor Then

            Continue For
        End If


        Dim hostPort As PortRecord = _
            GetHostSidePortForFlange( _
                n, _
                edges)


        If hostPort Is Nothing Then
            Continue For
        End If


        Dim innerP As SvgPoint = _
            MapCanonicalPoint( _
                transform, _
                hostPort.X, _
                hostPort.Y, _
                hostPort.Z)

        Dim outerP As SvgPoint = _
            MapCanonicalPoint( _
                transform, _
                n.OuterX, _
                n.OuterY, _
                n.OuterZ)


        svg.AppendLine( _
            "<line x1=""" & Num(innerP.X) & _
            """ y1=""" & Num(innerP.Y) & _
            """ x2=""" & Num(outerP.X) & _
            """ y2=""" & Num(outerP.Y) & _
            """ stroke=""black"" stroke-width=""4""/>")


        DrawPerpendicularFaceLine( _
            svg, _
            innerP, _
            outerP, _
            innerP, _
            42)


        DrawPerpendicularFaceLine( _
            svg, _
            innerP, _
            outerP, _
            outerP, _
            54)

    Next


    ' ---------------------------------------------------------------
    ' Elbow arcs.
    ' ---------------------------------------------------------------

    For Each n As NodeRecord In nodes


        If n.ComponentType <> "ELBOW" Then
            Continue For
        End If


        Dim ports As List(Of PortRecord) = _
            GetUsedPorts(n, edges)


        If ports.Count < 2 Then
            Continue For
        End If


        Dim p1 As PortRecord = ports.Item(0)
        Dim p2 As PortRecord = ports.Item(1)


        DrawElbowArc( _
            svg, _
            n, _
            p1, _
            p2, _
            transform)

    Next


    ' ---------------------------------------------------------------
    ' Terminal caps for non-flange endpoints.
    ' ---------------------------------------------------------------

    For Each n As NodeRecord In nodes


        If n.Neighbours.Count <> 1 Then
            Continue For
        End If


        If n.ComponentType = "FLANGE" Then
            Continue For
        End If


        Dim active As List(Of PortRecord) = _
            GetUsedPorts(n, edges)


        If active.Count = 0 Then
            Continue For
        End If


        ' Choose unused geometric port farthest from used port if known.
        Dim endPoint As Point3DRecord = Nothing


        If active.Count >= 2 Then

            ' Endpoint component can still have two used ports in odd cases.
            endPoint = _
                New Point3DRecord( _
                    n.RefX, n.RefY, n.RefZ)

        Else

            Dim used As PortRecord = active.Item(0)
            Dim best As PortRecord = Nothing
            Dim bestD As Double = -1


            For Each candidate As PortRecord In n.Ports


                Dim d As Double = _
                    Dist3D( _
                        used.X, used.Y, used.Z, _
                        candidate.X, candidate.Y, candidate.Z)


                If d > bestD Then

                    bestD = d
                    best = candidate

                End If

            Next


            If best IsNot Nothing Then

                endPoint = _
                    New Point3DRecord( _
                        best.X, best.Y, best.Z)

            End If

        End If


        If endPoint IsNot Nothing Then


            Dim ep As SvgPoint = _
                MapCanonicalPoint( _
                    transform, _
                    endPoint.X, _
                    endPoint.Y, _
                    endPoint.Z)


            Dim np As SvgPoint = _
                MapCanonicalPoint( _
                    transform, _
                    n.Neighbours.Item(0).RefX, _
                    n.Neighbours.Item(0).RefY, _
                    n.Neighbours.Item(0).RefZ)


            DrawPerpendicularEndCap( _
                svg, _
                ep, _
                np, _
                34)

        End If

    Next

End Sub



Sub DrawPerpendicularFaceLine( _
    svg As StringBuilder, _
    axisA As SvgPoint, _
    axisB As SvgPoint, _
    center As SvgPoint, _
    length As Double)


    Dim dx As Double = axisB.X - axisA.X
    Dim dy As Double = axisB.Y - axisA.Y


    Dim dl As Double = _
        Math.Sqrt( _
            dx * dx + _
            dy * dy)


    If dl < 0.001 Then
        Exit Sub
    End If


    dx /= dl
    dy /= dl


    Dim nx As Double = -dy
    Dim ny As Double = dx


    Dim half As Double = length / 2.0


    svg.AppendLine( _
        "<line x1=""" & Num(center.X - nx * half) & _
        """ y1=""" & Num(center.Y - ny * half) & _
        """ x2=""" & Num(center.X + nx * half) & _
        """ y2=""" & Num(center.Y + ny * half) & _
        """ stroke=""black"" stroke-width=""4""/>")

End Sub



Sub DrawPerpendicularEndCap( _
    svg As StringBuilder, _
    endPoint As SvgPoint, _
    towardPoint As SvgPoint, _
    length As Double)


    DrawPerpendicularFaceLine( _
        svg, _
        endPoint, _
        towardPoint, _
        endPoint, _
        length)

End Sub



Sub DrawElbowArc( _
    svg As StringBuilder, _
    elbow As NodeRecord, _
    port1 As PortRecord, _
    port2 As PortRecord, _
    transform As SchematicTransform)


    Dim c As SvgPoint = _
        MapCanonicalPoint( _
            transform, _
            elbow.RefX, _
            elbow.RefY, _
            elbow.RefZ)

    Dim a As SvgPoint = _
        MapCanonicalPoint( _
            transform, _
            port1.X, _
            port1.Y, _
            port1.Z)

    Dim b As SvgPoint = _
        MapCanonicalPoint( _
            transform, _
            port2.X, _
            port2.Y, _
            port2.Z)


    Dim radiusPixels As Double = _
        Math.Sqrt( _
            (a.X - c.X) * (a.X - c.X) + _
            (a.Y - c.Y) * (a.Y - c.Y))


    If radiusPixels < 1 Then
        Exit Sub
    End If


    Dim v1x As Double = a.X - c.X
    Dim v1y As Double = a.Y - c.Y

    Dim v2x As Double = b.X - c.X
    Dim v2y As Double = b.Y - c.Y


    Dim cross2d As Double = _
        v1x * v2y - _
        v1y * v2x


    Dim sweep As Integer = 0


    If cross2d > 0 Then
        sweep = 1
    End If


    svg.AppendLine( _
        "<path d=""M " & _
        Num(a.X) & " " & Num(a.Y) & _
        " A " & _
        Num(radiusPixels) & " " & Num(radiusPixels) & _
        " 0 0 " & sweep.ToString() & " " & _
        Num(b.X) & " " & Num(b.Y) & _
        """ fill=""none"" stroke=""black"" stroke-width=""4""/>")

End Sub



' ===================================================================
' COMPONENT LABELS
' ===================================================================

Sub DrawComponentLabels( _
    svg As StringBuilder, _
    nodes As List(Of NodeRecord), _
    transform As SchematicTransform)


    For Each n As NodeRecord In nodes


        Dim p As SvgPoint = _
            MapCanonicalPoint( _
                transform, _
                n.RefX, _
                n.RefY, _
                n.RefZ)


        svg.AppendLine( _
            "<circle cx=""" & Num(p.X) & _
            """ cy=""" & Num(p.Y) & _
            """ r=""3"" fill=""white"" stroke=""black"" stroke-width=""1""/>")


        svg.AppendLine( _
            "<text x=""" & Num(p.X + 8) & _
            """ y=""" & Num(p.Y - 8) & _
            """ font-family=""Arial"" font-size=""12"" font-weight=""bold"">" & _
            XmlText(n.Code) & _
            "</text>")

    Next

End Sub



' ===================================================================
' DIMENSION DRAWING
' ===================================================================

Sub DrawAllDimensions( _
    svg As StringBuilder, _
    componentDimensions As List(Of DimensionRecord), _
    chains As List(Of StraightChain), _
    overallDimensions As List(Of DimensionRecord), _
    transform As SchematicTransform)


    Dim longestChainIndex As Integer = 0
    Dim longestLength As Double = -1


    For Each c As StraightChain In chains

        If c.Length > longestLength Then

            longestLength = c.Length
            longestChainIndex = c.Index

        End If

    Next


    For Each chain As StraightChain In chains


        Dim chainA As SvgPoint = _
            MapCanonicalPoint( _
                transform, _
                chain.X1, _
                chain.Y1, _
                chain.Z1)

        Dim chainB As SvgPoint = _
            MapCanonicalPoint( _
                transform, _
                chain.X2, _
                chain.Y2, _
                chain.Z2)


        Dim normalX As Double = 0
        Dim normalY As Double = 0


        ChooseDimensionNormal( _
            chainA, _
            chainB, _
            chain.Index = longestChainIndex, _
            normalX, _
            normalY)


        ' -----------------------------------------------------------
        ' Component dimensions belonging to this straight run.
        ' All share one dimension level.
        ' -----------------------------------------------------------

        For Each d As DimensionRecord In componentDimensions


            If d.ChainIndex <> chain.Index Then
                Continue For
            End If


            DrawOneDimension( _
                svg, _
                d, _
                transform, _
                normalX, _
                normalY, _
                30.0, _
                False)

        Next


        ' -----------------------------------------------------------
        ' Overall dimension on a farther level.
        ' -----------------------------------------------------------

        For Each d As DimensionRecord In overallDimensions


            If d.ChainIndex <> chain.Index Then
                Continue For
            End If


            DrawOneDimension( _
                svg, _
                d, _
                transform, _
                normalX, _
                normalY, _
                66.0, _
                True)

        Next

    Next


    ' ---------------------------------------------------------------
    ' Any component dimension not assigned to a chain.
    ' ---------------------------------------------------------------

    For Each d As DimensionRecord In componentDimensions


        If d.ChainIndex <> 0 Then
            Continue For
        End If


        Dim a As SvgPoint = _
            MapCanonicalPoint( _
                transform, _
                d.X1, d.Y1, d.Z1)

        Dim b As SvgPoint = _
            MapCanonicalPoint( _
                transform, _
                d.X2, d.Y2, d.Z2)


        Dim nx As Double = 0
        Dim ny As Double = 0


        ChooseDimensionNormal( _
            a, b, _
            False, _
            nx, ny)


        DrawOneDimension( _
            svg, _
            d, _
            transform, _
            nx, ny, _
            30.0, _
            False)

    Next

End Sub



Sub ChooseDimensionNormal( _
    a As SvgPoint, _
    b As SvgPoint, _
    isLongestMainRun As Boolean, _
    ByRef nx As Double, _
    ByRef ny As Double)


    Dim dx As Double = b.X - a.X
    Dim dy As Double = b.Y - a.Y


    Dim dl As Double = _
        Math.Sqrt( _
            dx * dx + _
            dy * dy)


    If dl < 0.001 Then

        nx = 0
        ny = 1

        Exit Sub

    End If


    dx /= dl
    dy /= dl


    nx = -dy
    ny = dx


    ' ---------------------------------------------------------------
    ' Primary longest run:
    ' always place dimensions below the main run.
    ' ---------------------------------------------------------------

    If isLongestMainRun Then


        If ny < 0 Then

            nx *= -1
            ny *= -1

        End If


        Exit Sub

    End If


    ' ---------------------------------------------------------------
    ' Secondary near-vertical runs:
    ' put dimensions to the right.
    ' ---------------------------------------------------------------

    If Math.Abs(dy) > Math.Abs(dx) Then


        If nx < 0 Then

            nx *= -1
            ny *= -1

        End If


    Else

        ' Other secondary horizontal runs: below.
        If ny < 0 Then

            nx *= -1
            ny *= -1

        End If

    End If

End Sub



Sub DrawOneDimension( _
    svg As StringBuilder, _
    d As DimensionRecord, _
    transform As SchematicTransform, _
    nx As Double, _
    ny As Double, _
    offset As Double, _
    isOverall As Boolean)


    Dim a As SvgPoint = _
        MapCanonicalPoint( _
            transform, _
            d.X1, d.Y1, d.Z1)

    Dim b As SvgPoint = _
        MapCanonicalPoint( _
            transform, _
            d.X2, d.Y2, d.Z2)


    Dim da As New SvgPoint( _
        a.X + nx * offset, _
        a.Y + ny * offset)

    Dim db As New SvgPoint( _
        b.X + nx * offset, _
        b.Y + ny * offset)


    Dim strokeWidth As Double = 1.0


    If isOverall Then
        strokeWidth = 1.5
    End If


    ' Extension lines.
    svg.AppendLine( _
        "<line x1=""" & Num(a.X) & _
        """ y1=""" & Num(a.Y) & _
        """ x2=""" & Num(da.X) & _
        """ y2=""" & Num(da.Y) & _
        """ stroke=""black"" stroke-width=""0.8""/>")


    svg.AppendLine( _
        "<line x1=""" & Num(b.X) & _
        """ y1=""" & Num(b.Y) & _
        """ x2=""" & Num(db.X) & _
        """ y2=""" & Num(db.Y) & _
        """ stroke=""black"" stroke-width=""0.8""/>")


    ' Dimension line.
    svg.AppendLine( _
        "<line x1=""" & Num(da.X) & _
        """ y1=""" & Num(da.Y) & _
        """ x2=""" & Num(db.X) & _
        """ y2=""" & Num(db.Y) & _
        """ stroke=""black"" stroke-width=""" & _
        Num(strokeWidth) & """/>") 


    ' Ticks.
    DrawDimensionTick(svg, da, db)
    DrawDimensionTick(svg, db, da)


    Dim mx As Double = (da.X + db.X) / 2.0
    Dim my As Double = (da.Y + db.Y) / 2.0


    Dim angle As Double = _
        Math.Atan2( _
            db.Y - da.Y, _
            db.X - da.X) * _
        180.0 / Math.PI


    If angle > 90 Then
        angle -= 180
    End If


    If angle < -90 Then
        angle += 180
    End If


    Dim textValue As String = _
        Math.Round(d.Value, 1) _
            .ToString( _
                "0.#", _
                CultureInfo.InvariantCulture)


    If isOverall Then
        textValue = textValue
    End If


    svg.AppendLine( _
        "<text x=""" & Num(mx) & _
        """ y=""" & Num(my - 5) & _
        """ text-anchor=""middle"" " & _
        "font-family=""Arial"" font-size=""" & _
        If(isOverall, "14", "12") & _
        """ font-weight=""" & _
        If(isOverall, "bold", "normal") & _
        """ transform=""rotate(" & _
        Num(angle) & " " & _
        Num(mx) & " " & _
        Num(my - 5) & ")"">" & _
        XmlText(textValue) & _
        "</text>")

End Sub



Sub DrawDimensionTick( _
    svg As StringBuilder, _
    atPoint As SvgPoint, _
    toward As SvgPoint)


    Dim dx As Double = toward.X - atPoint.X
    Dim dy As Double = toward.Y - atPoint.Y


    Dim dl As Double = _
        Math.Sqrt( _
            dx * dx + _
            dy * dy)


    If dl < 0.001 Then
        Exit Sub
    End If


    dx /= dl
    dy /= dl


    Dim nx As Double = -dy
    Dim ny As Double = dx


    Dim half As Double = 6


    svg.AppendLine( _
        "<line x1=""" & Num(atPoint.X - nx * half) & _
        """ y1=""" & Num(atPoint.Y - ny * half) & _
        """ x2=""" & Num(atPoint.X + nx * half) & _
        """ y2=""" & Num(atPoint.Y + ny * half) & _
        """ stroke=""black"" stroke-width=""1""/>")

End Sub



' ===================================================================
' DIMENSION SUMMARY TABLE
' ===================================================================

Sub DrawDimensionSummaryTable( _
    svg As StringBuilder, _
    componentDimensions As List(Of DimensionRecord), _
    overallDimensions As List(Of DimensionRecord), _
    x As Double, _
    y As Double)


    svg.AppendLine( _
        "<text x=""" & Num(x) & _
        """ y=""" & Num(y) & _
        """ font-family=""Arial"" font-size=""14"" font-weight=""bold"">" & _
        "EXTRACTED DIMENSIONS" & _
        "</text>")


    Dim cursorX As Double = x
    Dim cursorY As Double = y + 24


    For Each d As DimensionRecord In componentDimensions


        svg.AppendLine( _
            "<text x=""" & Num(cursorX) & _
            """ y=""" & Num(cursorY) & _
            """ font-family=""Arial"" font-size=""11"">" & _
            XmlText( _
                d.Label & _
                " = " & _
                FormatMm(d.Value)) & _
            "</text>")


        cursorY += 18


        If cursorY > 1020 Then

            cursorX += 260
            cursorY = y + 24

        End If

    Next


    cursorX += 320
    cursorY = y + 24


    For Each d As DimensionRecord In overallDimensions


        svg.AppendLine( _
            "<text x=""" & Num(cursorX) & _
            """ y=""" & Num(cursorY) & _
            """ font-family=""Arial"" font-size=""12"" font-weight=""bold"">" & _
            XmlText( _
                d.Label & _
                " = " & _
                FormatMm(d.Value)) & _
            "</text>")


        cursorY += 20

    Next

End Sub



' ===================================================================
' PORT / NODE HELPERS
' ===================================================================

Function GetHostSidePortForFlange( _
    flange As NodeRecord, _
    edges As List(Of EdgeRecord)) As PortRecord


    For Each e As EdgeRecord In edges


        If e.A Is flange Then

            Return e.PortB

        ElseIf e.B Is flange Then

            Return e.PortA

        End If

    Next


    Return Nothing

End Function



Function GetUsedPorts( _
    node As NodeRecord, _
    edges As List(Of EdgeRecord)) As List(Of PortRecord)


    Dim result As New List(Of PortRecord)


    For Each e As EdgeRecord In edges


        If e.A Is node Then

            AddPortReferenceIfMissing( _
                result, _
                e.PortA)

        ElseIf e.B Is node Then

            AddPortReferenceIfMissing( _
                result, _
                e.PortB)

        End If

    Next


    Return result

End Function



Sub AddPortReferenceIfMissing( _
    list As List(Of PortRecord), _
    port As PortRecord)


    For Each p As PortRecord In list

        If p Is port Then
            Exit Sub
        End If

    Next


    list.Add(port)

End Sub



Sub FindFarthestPortPair( _
    ports As List(Of PortRecord), _
    ByRef outA As PortRecord, _
    ByRef outB As PortRecord)


    outA = Nothing
    outB = Nothing


    Dim best As Double = -1


    For i As Integer = 0 To ports.Count - 2

        For j As Integer = i + 1 To ports.Count - 1


            Dim a As PortRecord = ports.Item(i)
            Dim b As PortRecord = ports.Item(j)


            Dim d As Double = _
                Dist3D( _
                    a.X, a.Y, a.Z, _
                    b.X, b.Y, b.Z)


            If d > best Then

                best = d
                outA = a
                outB = b

            End If

        Next

    Next

End Sub



Sub FindMostOpposedPortPair( _
    ports As List(Of PortRecord), _
    ByRef outA As PortRecord, _
    ByRef outB As PortRecord)


    outA = Nothing
    outB = Nothing


    Dim bestDot As Double = Double.MaxValue


    For i As Integer = 0 To ports.Count - 2

        For j As Integer = i + 1 To ports.Count - 1


            Dim a As PortRecord = ports.Item(i)
            Dim b As PortRecord = ports.Item(j)


            Dim dotValue As Double = _
                NormalDot(a, b)


            If dotValue < bestDot Then

                bestDot = dotValue
                outA = a
                outB = b

            End If

        Next

    Next

End Sub



Function ClosestAxisIntersection( _
    a As PortRecord, _
    b As PortRecord, _
    ByRef outX As Double, _
    ByRef outY As Double, _
    ByRef outZ As Double, _
    ByRef separation As Double) As Boolean


    Dim p1x As Double = a.X
    Dim p1y As Double = a.Y
    Dim p1z As Double = a.Z

    Dim p2x As Double = b.X
    Dim p2y As Double = b.Y
    Dim p2z As Double = b.Z


    Dim d1x As Double = a.NX
    Dim d1y As Double = a.NY
    Dim d1z As Double = a.NZ

    Dim d2x As Double = b.NX
    Dim d2y As Double = b.NY
    Dim d2z As Double = b.NZ


    Dim rx As Double = p1x - p2x
    Dim ry As Double = p1y - p2y
    Dim rz As Double = p1z - p2z


    Dim aa As Double = _
        d1x * d1x + _
        d1y * d1y + _
        d1z * d1z

    Dim bb As Double = _
        d1x * d2x + _
        d1y * d2y + _
        d1z * d2z

    Dim cc As Double = _
        d2x * d2x + _
        d2y * d2y + _
        d2z * d2z

    Dim dd As Double = _
        d1x * rx + _
        d1y * ry + _
        d1z * rz

    Dim ee As Double = _
        d2x * rx + _
        d2y * ry + _
        d2z * rz


    Dim denominator As Double = _
        aa * cc - _
        bb * bb


    If Math.Abs(denominator) < 0.0000001 Then
        Return False
    End If


    Dim t As Double = _
        (bb * ee - cc * dd) / denominator

    Dim s As Double = _
        (aa * ee - bb * dd) / denominator


    Dim c1x As Double = p1x + t * d1x
    Dim c1y As Double = p1y + t * d1y
    Dim c1z As Double = p1z + t * d1z

    Dim c2x As Double = p2x + s * d2x
    Dim c2y As Double = p2y + s * d2y
    Dim c2z As Double = p2z + s * d2z


    outX = (c1x + c2x) / 2.0
    outY = (c1y + c2y) / 2.0
    outZ = (c1z + c2z) / 2.0


    separation = _
        Dist3D( _
            c1x, c1y, c1z, _
            c2x, c2y, c2z)


    Return True

End Function



' ===================================================================
' GRAPH / CLASSIFICATION HELPERS
' ===================================================================

Sub AssignDisplayCodes( _
    nodes As List(Of NodeRecord))


    Dim counters As New Dictionary(Of String, Integer)


    For Each n As NodeRecord In nodes


        Dim prefix As String = "X"


        Select Case n.ComponentType

            Case "FLANGE"
                prefix = "F"

            Case "ELBOW"
                prefix = "E"

            Case "TEE"
                prefix = "T"

            Case "PIPE"
                prefix = "P"

            Case "REDUCER"
                prefix = "R"

            Case "VALVE"
                prefix = "V"

            Case "COUPLING_SOCKET"
                prefix = "C"

            Case Else
                prefix = "X"

        End Select


        If Not counters.ContainsKey(prefix) Then
            counters.Add(prefix, 0)
        End If


        counters(prefix) = _
            counters(prefix) + 1


        n.Code = _
            prefix & _
            counters(prefix).ToString()

    Next

End Sub



Function CountGraphGroups( _
    nodes As List(Of NodeRecord)) As Integer


    Dim visited As New HashSet(Of NodeRecord)
    Dim groups As Integer = 0


    For Each n As NodeRecord In nodes


        If visited.Contains(n) Then
            Continue For
        End If


        groups += 1

        FloodVisit(n, visited)

    Next


    Return groups

End Function



Sub FloodVisit( _
    node As NodeRecord, _
    visited As HashSet(Of NodeRecord))


    If visited.Contains(node) Then
        Exit Sub
    End If


    visited.Add(node)


    For Each nextNode As NodeRecord In node.Neighbours

        FloodVisit( _
            nextNode, _
            visited)

    Next

End Sub



Function HasConnection( _
    edges As List(Of EdgeRecord), _
    a As NodeRecord, _
    b As NodeRecord) As Boolean


    For Each e As EdgeRecord In edges


        If e.A Is a AndAlso e.B Is b Then
            Return True
        End If


        If e.A Is b AndAlso e.B Is a Then
            Return True
        End If

    Next


    Return False

End Function



Function GetNeighbourCodes( _
    node As NodeRecord) As List(Of String)


    Dim result As New List(Of String)


    For Each n As NodeRecord In node.Neighbours

        result.Add(n.Code)

    Next


    Return result

End Function



Function GuessComponentType( _
    partNumber As String, _
    description As String, _
    occurrenceName As String) As String


    Dim text As String = _
        (partNumber & " " & _
         description & " " & _
         occurrenceName).ToLowerInvariant()


    If Regex.IsMatch(text, "\bflange\b") Then

        Return "FLANGE"

    ElseIf Regex.IsMatch(text, "\breducer\b") Then

        Return "REDUCER"

    ElseIf Regex.IsMatch(text, "\b(elbow|bend)\b") Then

        Return "ELBOW"

    ElseIf Regex.IsMatch(text, "\btee\b") Then

        Return "TEE"

    ElseIf Regex.IsMatch(text, "\bvalve\b") Then

        Return "VALVE"

    ElseIf Regex.IsMatch( _
        text, _
        "\b(socket|coupling|union)\b") Then

        Return "COUPLING_SOCKET"

    ElseIf Regex.IsMatch(text, "\b(pipe|tube)\b") Then

        Return "PIPE"

    End If


    Return "OTHER"

End Function



' ===================================================================
' MATH / IO HELPERS
' ===================================================================

Sub AddPortIfUnique( _
    ports As List(Of PortRecord), _
    newPort As PortRecord)


    For Each existing As PortRecord In ports


        Dim separation As Double = _
            Dist3D( _
                existing.X, _
                existing.Y, _
                existing.Z, _
                newPort.X, _
                newPort.Y, _
                newPort.Z)


        If separation < 0.1 Then


            Dim alignment As Double = _
                Math.Abs( _
                    NormalDot( _
                        existing, _
                        newPort))


            If alignment > 0.99 Then
                Exit Sub
            End If

        End If

    Next


    ports.Add(newPort)

End Sub



Function NormalDot( _
    a As PortRecord, _
    b As PortRecord) As Double


    Return _
        a.NX * b.NX + _
        a.NY * b.NY + _
        a.NZ * b.NZ

End Function



Function Dist3D( _
    x1 As Double, _
    y1 As Double, _
    z1 As Double, _
    x2 As Double, _
    y2 As Double, _
    z2 As Double) As Double


    Dim dx As Double = x2 - x1
    Dim dy As Double = y2 - y1
    Dim dz As Double = z2 - z1


    Return _
        Math.Sqrt( _
            dx * dx + _
            dy * dy + _
            dz * dz)

End Function



Sub NormalizeVector( _
    ByRef x As Double, _
    ByRef y As Double, _
    ByRef z As Double)


    Dim l As Double = _
        Math.Sqrt( _
            x * x + _
            y * y + _
            z * z)


    If l < 0.000001 Then

        x = 1
        y = 0
        z = 0

        Exit Sub

    End If


    x /= l
    y /= l
    z /= l

End Sub



Function GetIProperty( _
    doc As Document, _
    propertySetName As String, _
    propertyName As String) As String


    Try

        Return _
            doc.PropertySets _
               .Item(propertySetName) _
               .Item(propertyName) _
               .Value _
               .ToString() _
               .Trim()

    Catch

        Return ""

    End Try

End Function



Function Csv(value As String) As String


    If value Is Nothing Then
        value = ""
    End If


    Return _
        """" & _
        value.Replace("""", """""") & _
        """"

End Function



Function Num(value As Double) As String


    Return _
        value.ToString( _
            "0.###", _
            CultureInfo.InvariantCulture)

End Function



Function FormatMm(value As Double) As String


    Return _
        Math.Round(value, 1) _
            .ToString( _
                "0.#", _
                CultureInfo.InvariantCulture) & _
        " mm"

End Function



Function XmlText(value As String) As String


    If value Is Nothing Then
        Return ""
    End If


    Return _
        value.Replace("&", "&amp;") _
             .Replace("<", "&lt;") _
             .Replace(">", "&gt;") _
             .Replace("""", "&quot;")

End Function



Function SafeFileName(value As String) As String


    For Each invalidChar As Char In _
        System.IO.Path.GetInvalidFileNameChars()


        value = _
            value.Replace( _
                invalidChar, _
                "_"c)

    Next


    Return value

End Function



' ===================================================================
' DATA CLASSES
' ===================================================================

Class NodeRecord

    Public OccurrenceName As String = ""

    Public PartNumber As String = ""
    Public Description As String = ""

    Public ComponentType As String = "OTHER"
    Public Code As String = ""


    Public X As Double
    Public Y As Double
    Public Z As Double


    Public Ports As New List(Of PortRecord)
    Public Neighbours As New List(Of NodeRecord)


    Public RefX As Double
    Public RefY As Double
    Public RefZ As Double

    Public ReferenceType As String = ""


    ' Flange manufacturing reference.
    Public HasOuterAnchor As Boolean = False

    Public InnerFaceIndex As Integer = 0
    Public OuterFaceIndex As Integer = 0

    Public OuterX As Double
    Public OuterY As Double
    Public OuterZ As Double

    Public OuterOffset As Double

    Public FlangeHostCode As String = ""

    Public HostPortX As Double
    Public HostPortY As Double
    Public HostPortZ As Double

End Class



Class PortRecord

    Public Owner As NodeRecord

    Public FaceIndex As Integer


    Public X As Double
    Public Y As Double
    Public Z As Double


    Public NX As Double
    Public NY As Double
    Public NZ As Double


    Public Radius As Double

    Public CircularEdges As Integer
    Public FaceArea As Double


    Public Used As Boolean = False

End Class



Class EdgeRecord

    Public A As NodeRecord
    Public B As NodeRecord

    Public PortA As PortRecord
    Public PortB As PortRecord

    Public ConnectionType As String = ""

    Public ConnectionDistance As Double

End Class



Class PrimitiveSegment

    Public Owner As NodeRecord
    Public Kind As String = ""

    Public X1 As Double
    Public Y1 As Double
    Public Z1 As Double

    Public X2 As Double
    Public Y2 As Double
    Public Z2 As Double

    Public Length As Double


    Public Sub New( _
        ownerNode As NodeRecord, _
        primitiveKind As String, _
        ax As Double, _
        ay As Double, _
        az As Double, _
        bx As Double, _
        by As Double, _
        bz As Double)


        Owner = ownerNode
        Kind = primitiveKind

        X1 = ax
        Y1 = ay
        Z1 = az

        X2 = bx
        Y2 = by
        Z2 = bz

        Dim dx As Double = bx - ax
        Dim dy As Double = by - ay
        Dim dz As Double = bz - az

        Length = _
            Math.Sqrt( _
                dx * dx + _
                dy * dy + _
                dz * dz)

    End Sub

End Class



Class DimensionRecord

    Public Label As String = ""
    Public OwnerCode As String = ""

    Public DimensionType As String = ""
    Public Category As String = ""

    Public X1 As Double
    Public Y1 As Double
    Public Z1 As Double

    Public X2 As Double
    Public Y2 As Double
    Public Z2 As Double

    Public Value As Double

    Public ChainIndex As Integer = 0

End Class



Class StraightChain

    Public Index As Integer = 0

    Public Segments As New List(Of PrimitiveSegment)

    Public X1 As Double
    Public Y1 As Double
    Public Z1 As Double

    Public X2 As Double
    Public Y2 As Double
    Public Z2 As Double

    Public Length As Double

End Class



Class Point3DRecord

    Public X As Double
    Public Y As Double
    Public Z As Double


    Public Sub New( _
        px As Double, _
        py As Double, _
        pz As Double)


        X = px
        Y = py
        Z = pz

    End Sub

End Class



Class SvgPoint

    Public X As Double
    Public Y As Double


    Public Sub New( _
        px As Double, _
        py As Double)


        X = px
        Y = py

    End Sub

End Class



Class SchematicTransform

    Public OriginX As Double
    Public OriginY As Double
    Public OriginZ As Double

    Public UX As Double
    Public UY As Double
    Public UZ As Double

    Public VX As Double
    Public VY As Double
    Public VZ As Double

    Public Scale As Double

    Public ScreenOriginX As Double
    Public ScreenOriginY As Double

End Class
